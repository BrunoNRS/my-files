EMAP-MIB DEFINITIONS ::= BEGIN
                                 IMPORTS
huaweiUtility
FROM HUAWEI-MIB
                                             OBJECT-GROUP, NOTIFICATION-GROUP
                                                 FROM SNMPv2-CONF
                                             Integer32, Unsigned32, OBJECT-TYPE, MODULE-IDENTITY, NOTIFICATION-TYPE
                                                 FROM SNMPv2-SMI
                                             TEXTUAL-CONVENTION
                                                 FROM SNMPv2-TC;
hwSiteMonitorMIB MODULE-IDENTITY
LAST-UPDATED "201210240000Z"
ORGANIZATION 
                                             "Huawei Technologies Co., Ltd."
CONTACT-INFO 
                                             "Floor 5, Block 4, R&D Building,
                                             Huawei Longgang Production Base,
                                             Shenzhen,   P.R.C.
                                             http: // www.huawei.com
                                             Zip: 518129."
DESCRIPTION 
                                             "EMAP MIB defines MIB objects which provides load and backup management, patch management NMS interfaces.
                                             The current version is v1.01"
REVISION "201210240000Z"
                                             DESCRIPTION 
                                             "Huawei emap mib v1.00"
::= { huaweiUtility 164 }

DisplayString ::= TEXTUAL-CONVENTION
                                             STATUS current
                                             DESCRIPTION 
                                             "Description."
                                             SYNTAX OCTET STRING (SIZE (1..64))
                                             
                                             RowStatus ::= TEXTUAL-CONVENTION
                                             STATUS current
                                             DESCRIPTION 
                                             "Description."
                                             SYNTAX INTEGER
                                             {
                                                     active(1),
                                                     notInService(2),
                                                     notReady(3),
                                                     createAndGo(4),
                                                     createAndWait(5),
                                                     destroy(6)
                                             }
                                             
                                             DateAndTime ::= TEXTUAL-CONVENTION
                                             STATUS current
                                             DESCRIPTION 
                                             "Description."
                                             SYNTAX OCTET STRING (SIZE (8..11))
                                             
                                             RunStatus ::= TEXTUAL-CONVENTION
                                             STATUS current
                                             DESCRIPTION 
                                                     "This integer value represents running status of the system. 
                                                     Depending on situation there may be limits on allowed values.
                                                     Operational values:
                                                     (1) unknown - status has not yet been defined
                                                     (2) normal - there are no activated alarms
                                                     (3) alarm - alarm status
                                             "
                                             SYNTAX INTEGER
                                             {
                                                     unknow(1),
                                                     normal(2),
                                                     alarm(3)
                                             }
                                             
                                             MeasuresRange ::= TEXTUAL-CONVENTION
                                             STATUS current
                                             DESCRIPTION 
                                             "Description."
                                             SYNTAX Integer32
                                             
                                             TruthValue ::= TEXTUAL-CONVENTION
                                             STATUS current
                                             DESCRIPTION 
                                             "Description."
                                             SYNTAX INTEGER
                                             {
                                                     true(1),
                                                     false(2)
                                             }
        hwSiteMonitorMIBObjects OBJECT IDENTIFIER ::= { hwSiteMonitorMIB 1 }

        hwSiteInfo OBJECT IDENTIFIER ::= { hwSiteMonitorMIBObjects 1 }

        hwSiteSummary OBJECT IDENTIFIER ::= { hwSiteInfo 1 }

        hwSiteId OBJECT-TYPE
            SYNTAX OCTET STRING (SIZE (0..64))
            MAX-ACCESS read-only
            STATUS current
            DESCRIPTION
                "Site ID, default value: 000,000.Naming rule of the site device ID (six digits): 
                The first three digits indicate the device name and the last three digits indicate the serial number (SN) of the device. 
                If the last three digits are 000, it indicates a virtual device."
            ::= { hwSiteSummary 1 }

        hwSiteName OBJECT-TYPE
            SYNTAX OCTET STRING (SIZE (0..63))
            MAX-ACCESS read-write
            STATUS current
            DESCRIPTION
                "Site name, which users can configure, is used to specify a site.  Otherwise, the configured character can not be any other languages except English."
            ::= { hwSiteSummary 2 }

        hwSiteAdminAddr OBJECT-TYPE
            SYNTAX Unsigned32 (0..65535)
            MAX-ACCESS read-write
            STATUS current
            DESCRIPTION
                "Site administrant address, which users can assigned, is the unique ID of a site. 
                It is used for device management by NMS, and value range is 0 to 65535. "
            ::= { hwSiteSummary 3 }

        hwSiteDescription OBJECT-TYPE
            SYNTAX OCTET STRING (SIZE (0..63))
            MAX-ACCESS read-write
            STATUS current
            DESCRIPTION
                "Site description. It is of the character string type. It is used to describe the site information such as the site location, which users can configure.  
                Otherwise, the configured character can not be any other languages except English."
            ::= { hwSiteSummary 4 }

        hwNetIdentifier OBJECT-TYPE
            SYNTAX OCTET STRING (SIZE (0..63))
            MAX-ACCESS read-write
            STATUS current
            DESCRIPTION
                "NE ID. It is of the character string type. It is the unique ID of the site (an independent network element (NE)) on the network. 
                Otherwise, the configured character can not be any other languages except English."
            ::= { hwSiteSummary 5 }

        hwSiteIp OBJECT-TYPE
            SYNTAX OCTET STRING (SIZE (8..16))
            MAX-ACCESS read-only
            STATUS current
            DESCRIPTION
                "Site IP address, default value is 192.168.0.10. Users need to configure the site IP address."
            ::= { hwSiteSummary 6 }

        hwSiteNetmask OBJECT-TYPE
            SYNTAX OCTET STRING (SIZE (8..16))
            MAX-ACCESS read-only
            STATUS current
            DESCRIPTION
                "Site netmask, default value is 255.255.255.0. Users need to configure the site netmask."
            ::= { hwSiteSummary 7 }

        hwSiteGateway OBJECT-TYPE
            SYNTAX OCTET STRING (SIZE (8..16))
            MAX-ACCESS read-only
            STATUS current
            DESCRIPTION
                "Site gateway, default value: 192.168.0.1. Users need to configure the site gateway."
            ::= { hwSiteSummary 8 }

        hwSiteDGWorkStatus OBJECT-TYPE
            SYNTAX INTEGER
                {
                idle(1),
                working(2),
                unknown(255)
                }
            MAX-ACCESS read-only
            STATUS current
            DESCRIPTION
                "State of the diesel working state. It is an enumeration type: 
                  If the enumeration value is 1, it indicates that the diesel is in the idle state;
                  If the enumeration value is 2, it indicates that the diesel is in the working state;     
                  If the enumeration value is 255, it indicates diesel operation status unknown."
            ::= { hwSiteSummary 9 }

        hwSiteRunningStatus OBJECT-TYPE
            SYNTAX INTEGER
                {
                normal(1),
                alarm(2)
                }
            MAX-ACCESS read-only
            STATUS current
            DESCRIPTION
                "State of the site alarm state. It is an enumeration type: 
                  If the enumeration value is 1, it indicates that the site is in the normal state;
                  If the enumeration value is 2, it indicates that the site is in the alarm state."
            ::= { hwSiteSummary 10 }

        hwSiteSystemEsn OBJECT-TYPE
            SYNTAX OCTET STRING (SIZE (8..16))
            MAX-ACCESS read-only
            STATUS current
            DESCRIPTION
                "System ESN Report Neteco"
            ::= { hwSiteSummary 12 }

        hwSiteTime OBJECT-TYPE
            SYNTAX OCTET STRING (SIZE (0..64))
            MAX-ACCESS read-write
            STATUS current
            DESCRIPTION
                "Set Site date and time, YYYY-MM-DD HH:MM:SS"
            ::= { hwSiteSummary 13 }

        hwSiteNetecoPrimaryServerIP OBJECT-TYPE
            SYNTAX OCTET STRING (SIZE (8..16))
            MAX-ACCESS read-only
            STATUS current
            DESCRIPTION
                "Neteco Primary Server IP Address"
            ::= { hwSiteSummary 14 }

        hwSiteNetecoBackupServerIP OBJECT-TYPE
            SYNTAX OCTET STRING (SIZE (8..16))
            MAX-ACCESS read-only
            STATUS current
            DESCRIPTION
                "Neteco Backup Server IP Address"
            ::= { hwSiteSummary 15 }

        hwSiteNetecoPortNumber OBJECT-TYPE
            SYNTAX Unsigned32
            MAX-ACCESS read-only
            STATUS current
            DESCRIPTION
                "Neteco Port Number"
            ::= { hwSiteSummary 16 }

        hwSiteAlarms OBJECT IDENTIFIER ::= { hwSiteInfo 2 }

        hwDeviceTrapOrdinalNumber OBJECT-TYPE
            SYNTAX Unsigned32 ( 0..4294967295)
            MAX-ACCESS read-write
            STATUS current
            DESCRIPTION
                "Site device event trap serial number (SN) is the unique ID of the device event trap. It is used to resend and synchronize event traps.
                Its value range is 0 to 4294967295. When the value exceeds the maximum value, the system automatically clears the value and numbers the alarm from 0 to 4294967295.   
                If the network management system (NMS) recieve the alarm number is not consequential, in such case that it notifies the SNMP agent the event trap number required.  
                So the monitor send the 100 event trap messages in maximum, after consequencial number required by NMS again. Specially, if NMS set the value to 0, the agent would clear the alarm queue automatically."
            ::= { hwSiteAlarms 1 }

        hwAlarmTrapOrdinalNumber OBJECT-TYPE
            SYNTAX Unsigned32 ( 0..4294967295)
            MAX-ACCESS read-write
            STATUS current
            DESCRIPTION
                "Site alarm serial number (SN) is the unique ID of the alarm Trap. It is used to resend and synchronize alarms. Its value range is 0 to 4294967295. When the value exceeds the maximum value, the system automatically clears the value and numbers the alarm from 0 to 4294967295.  
                If the network management system (NMS) recieve the alarm number is not consequential, in such case that it notifies the SNMP agent the alarm number required.  So the monitor send the 100 alarm messages in maximum, after consequencial number required by NMS again. Specially, if NMS set the value to 0, the agent would clear the alarm queue automatically."
            ::= { hwSiteAlarms 2 }

        hwAlarmQuantity OBJECT-TYPE
            SYNTAX Unsigned32 (0..65535)
            MAX-ACCESS read-only
            STATUS current
            DESCRIPTION
                "Alarm number in site alarm list which are support. 
                It is used for alarm list management by NMS, and value range is 0 to 65535. "
            ::= { hwSiteAlarms 3 }

        hwSiteActiveAlarmTable OBJECT-TYPE
            SYNTAX SEQUENCE OF HwSiteActiveAlarmEntry
            MAX-ACCESS not-accessible
             STATUS current
             DESCRIPTION
                ""
            ::= { hwSiteAlarms 99 }

        hwSiteActiveAlarmEntry OBJECT-TYPE
                        SYNTAX HwSiteActiveAlarmEntry
            MAX-ACCESS not-accessible
             STATUS current
             DESCRIPTION
                ""
            INDEX { hwActiveAlarmIndex }
            ::= { hwSiteActiveAlarmTable 1 }

        HwSiteActiveAlarmEntry            ::= SEQUENCE {
                hwActiveAlarmIndex
                    Integer32,
                hwActiveAlarmText
                    OCTET STRING,
                hwActiveAlarmLevel
                    INTEGER,
                hwActiveAlarmSigDesc
                    OCTET STRING,
                hwActiveAlarmTime
                    OCTET STRING,
                hwActiveAlarmRowStatus
                    RowStatus,
                hwSMUSiteName
                    OCTET STRING,
                hwSMUSiteAdminAddr
                    Unsigned32,
                hwSMUNetIdentifier
                    OCTET STRING,
                hwSMUSiteDescription
                    OCTET STRING,
                hwEquipId
                    Unsigned32,
                hwEquipName
                    OCTET STRING
            }

        hwActiveAlarmIndex OBJECT-TYPE
            SYNTAX Integer32 (1..65535)
            MAX-ACCESS read-only
            STATUS current
            DESCRIPTION
                "Site active alarm table index. It is the unique ID of the site alarm."
            ::= { hwSiteActiveAlarmEntry 1 }

        hwActiveAlarmText OBJECT-TYPE
            SYNTAX OCTET STRING (SIZE (0..63))
            MAX-ACCESS read-only
            STATUS current
            DESCRIPTION
                "Active alarm name. It is of the character string type, and used to specify the content of a specific alarm.  "
            ::= { hwSiteActiveAlarmEntry 2 }

        hwActiveAlarmLevel OBJECT-TYPE
            SYNTAX INTEGER
                {
                critical(1),
                major(2),
                minor(3),
                warning(4),
                unknown(255)
                }
            MAX-ACCESS read-only
            STATUS current
            DESCRIPTION
                "Active alarm level, which users can configure the alarm severity, is an enumeration type:
                    If the enumeration value is 1, it indicates a critical alarm;
                    If the enumeration value is 2, it indicates a major alarm;
                    If the enumeration value is 3, it indicates a minor alarm;
                    If the enumeration value is 4, it indicates a warning;
                    If the enumeration value is 255, it indicates a unknown;"
            ::= { hwSiteActiveAlarmEntry 3 }

        hwActiveAlarmSigDesc OBJECT-TYPE
            SYNTAX OCTET STRING (SIZE (0..127))
            MAX-ACCESS read-only
            STATUS current
            DESCRIPTION
                "Active alarm signal description. It is used to add and describe alarm content. Users can define the description of the alarm.
                  Otherwise, the configured character can not be any other languages except English."
            ::= { hwSiteActiveAlarmEntry 4 }

        hwActiveAlarmTime OBJECT-TYPE
            SYNTAX OCTET STRING (SIZE (0..127))
            MAX-ACCESS read-only
            STATUS current
            DESCRIPTION
                "Active alarm time. It is of the character string type, and used to specify the content of a specific alarm.  "
            ::= { hwSiteActiveAlarmEntry 5 }

        hwActiveAlarmRowStatus OBJECT-TYPE
            SYNTAX RowStatus
            MAX-ACCESS read-create
            STATUS current
            DESCRIPTION
                "Rowstatus of active alarm table."
            ::= { hwSiteActiveAlarmEntry 100 }

        hwSMUSiteName OBJECT-TYPE
            SYNTAX OCTET STRING (SIZE (0..63))
            MAX-ACCESS read-only
            STATUS current
            DESCRIPTION
                "Site name, which users can configure, is used to specify a site.  Otherwise, the configured character can not be any other languages except English."
            ::= { hwSiteActiveAlarmEntry 6 }

        hwSMUSiteAdminAddr OBJECT-TYPE
            SYNTAX Unsigned32 (0..65535)
            MAX-ACCESS read-only
            STATUS current
            DESCRIPTION
                "Site administrant address, which users can assigned, is the unique ID of a site. It is used for device management by NMS, and value range is 0 to 65535. "
            ::= { hwSiteActiveAlarmEntry 7 }

        hwSMUNetIdentifier OBJECT-TYPE
            SYNTAX OCTET STRING (SIZE (0..63))
            MAX-ACCESS read-only
            STATUS current
            DESCRIPTION
                "NE ID. It is of the character string type. It is the unique ID of the site (an independent network element (NE)) on the network. Otherwise, the configured character can not be any other languages except English."
            ::= { hwSiteActiveAlarmEntry 8 }

        hwSMUSiteDescription OBJECT-TYPE
            SYNTAX OCTET STRING (SIZE (0..63))
            MAX-ACCESS read-only
            STATUS current
            DESCRIPTION
                "Site description. It is of the character string type. It is used to describe the site information such as the site location, which users can configure.  Otherwise, the configured character can not be any other languages except English."
            ::= { hwSiteActiveAlarmEntry 9 }

        hwEquipId OBJECT-TYPE
            SYNTAX Unsigned32 (0..100)
            MAX-ACCESS read-only
            STATUS current
            DESCRIPTION
                "Equipment ID. Value range: 000,000 to 000,100, in which the first three digits indicate the device type and the last three digits indicate the device SN. "
            ::= { hwSiteActiveAlarmEntry 10 }

        hwEquipName OBJECT-TYPE
            SYNTAX OCTET STRING (SIZE (0..63))
            MAX-ACCESS read-only
            STATUS current
            DESCRIPTION
                "Equipment name. It is of the character string type, and users can set the name of the monitor. 
                Otherwise, the configured character can not be any other languages except English."
            ::= { hwSiteActiveAlarmEntry 11 }

        hwSiteAlarmTable OBJECT-TYPE
            SYNTAX SEQUENCE OF HwSiteAlarmEntry
            MAX-ACCESS not-accessible
             STATUS current
             DESCRIPTION
                "/"
            ::= { hwSiteAlarms 100 }

        hwSiteAlarmEntry OBJECT-TYPE
                        SYNTAX HwSiteAlarmEntry
            MAX-ACCESS not-accessible
             STATUS current
             DESCRIPTION
                "/"
            INDEX { hwAlarmIndex }
            ::= { hwSiteAlarmTable 1 }

        HwSiteAlarmEntry            ::= SEQUENCE {
                hwAlarmIndex
                    Unsigned32,
                hwAlarmText
                    OCTET STRING,
                hwAlarmLevel
                    INTEGER,
                hwAlarmSigDesc
                    OCTET STRING,
                hwAlarmRowStatus
                    RowStatus
            }

        hwAlarmIndex OBJECT-TYPE
            SYNTAX Unsigned32 (1..4294967295)
            MAX-ACCESS read-only
            STATUS current
            DESCRIPTION
                "Site alarm table index. It is the unique ID of the site alarm."
            ::= { hwSiteAlarmEntry 1 }

        hwAlarmText OBJECT-TYPE
            SYNTAX OCTET STRING (SIZE (0..63))
            MAX-ACCESS read-only
            STATUS current
            DESCRIPTION
                "Alarm name. It is of the character string type, and used to specify the content of a specific alarm.  "
            ::= { hwSiteAlarmEntry 2 }

        hwAlarmLevel OBJECT-TYPE
            SYNTAX INTEGER
                {
                critical(1),
                major(2),
                minor(3),
                warning(4),
                unknown(255)
                }
            MAX-ACCESS read-write
            STATUS current
            DESCRIPTION
                "Alarm level, which users can configure the alarm severity, is an enumeration type:
                  If the enumeration value is 1, it indicates a critical alarm;
                  If the enumeration value is 2, it indicates a major alarm;
                  If the enumeration value is 3, it indicates a minor alarm;
                  If the enumeration value is 4, it indicates a warning; "
            ::= { hwSiteAlarmEntry 3 }

        hwAlarmSigDesc OBJECT-TYPE
            SYNTAX OCTET STRING (SIZE (0..127))
            MAX-ACCESS read-only
            STATUS current
            DESCRIPTION
                "Alarm signal description. It is used to add and describe alarm content. Users can define the description of the alarm. 
                Otherwise, the configured character can not be any other languages except English."
            ::= { hwSiteAlarmEntry 4 }

        hwAlarmRowStatus OBJECT-TYPE
            SYNTAX RowStatus
            MAX-ACCESS read-create
            STATUS current
            DESCRIPTION
                "RowStatus of site alarms table."
            ::= { hwSiteAlarmEntry 100 }

        hwSiteStatus OBJECT IDENTIFIER ::= { hwSiteInfo 3 }

        hwAcInputStatus OBJECT-TYPE
            SYNTAX INTEGER
                {
                noalarm(0),
                alarm(1)
                }
            MAX-ACCESS read-only
            STATUS current
            DESCRIPTION
                "AC fail
                0: no alarm, 1:alarm"
            ::= { hwSiteStatus 1 }

        hwRectifierStatus OBJECT-TYPE
            SYNTAX INTEGER
                {
                noalarm(0),
                alarm(1)
                }
            MAX-ACCESS read-only
            STATUS current
            DESCRIPTION
                "Rectifier fault
                 0: no alarm, 1:alarm"
            ::= { hwSiteStatus 2 }

        hwBatteryDischarge OBJECT-TYPE
            SYNTAX INTEGER
                {
                noalarm(0),
                alarm(1)
                }
            MAX-ACCESS read-only
            STATUS current
            DESCRIPTION
                "Battery discharge
                0: no alarm, 1:alarm"
            ::= { hwSiteStatus 3 }

        hwBatteryLowVoltage OBJECT-TYPE
            SYNTAX INTEGER
                {
                noalarm(0),
                alarm(1)
                }
            MAX-ACCESS read-only
            STATUS current
            DESCRIPTION
                "Battery low voltage
                 0: no alarm, 1:alarm"
            ::= { hwSiteStatus 4 }

        hwBatteryUltraLowVoltage OBJECT-TYPE
            SYNTAX INTEGER
                {
                noalarm(0),
                alarm(1)
                }
            MAX-ACCESS read-only
            STATUS current
            DESCRIPTION
                "Battery ultra-low voltage
                 0: no alarm, 1:alarm"
            ::= { hwSiteStatus 5 }

        hwBatteryDisconnect OBJECT-TYPE
            SYNTAX INTEGER
                {
                noalarm(0),
                alarm(1)
                }
            MAX-ACCESS read-only
            STATUS current
            DESCRIPTION
                "Battery disconnect
                 0: no alarm, 1:alarm"
            ::= { hwSiteStatus 6 }

        hwFuseBroken OBJECT-TYPE
            SYNTAX INTEGER
                {
                noalarm(0),
                alarm(1)
                }
            MAX-ACCESS read-only
            STATUS current
            DESCRIPTION
                "Load fuse or battery fuse broken
                 0: no alarm, 1:alarm"
            ::= { hwSiteStatus 7 }

        hwLowRecitiferCapacity OBJECT-TYPE
            SYNTAX INTEGER
                {
                noalarm(0),
                alarm(1)
                }
            MAX-ACCESS read-only
            STATUS current
            DESCRIPTION
                "large load current and low rectifier capacity
                 0: no alarm, 1:alarm"
            ::= { hwSiteStatus 8 }

        hwBatteryTestNegative OBJECT-TYPE
            SYNTAX INTEGER
                {
                noalarm(0),
                alarm(1)
                }
            MAX-ACCESS read-only
            STATUS current
            DESCRIPTION
                "Battery test result negative
                 0: no alarm, 1:alarm"
            ::= { hwSiteStatus 9 }

        hwUrgentAlarmStatus OBJECT-TYPE
            SYNTAX INTEGER
                {
                noalarm(0),
                alarm(1)
                }
            MAX-ACCESS read-only
            STATUS current
            DESCRIPTION
                "Urgent Alarm
                 0: no alarm, 1:alarm"
            ::= { hwSiteStatus 10 }

        hwNonurgentAlarmStatus OBJECT-TYPE
            SYNTAX INTEGER
                {
                noalarm(0),
                alarm(1)
                }
            MAX-ACCESS read-only
            STATUS current
            DESCRIPTION
                "Non-Urgent Alarm
                 0: no alarm, 1:alarm"
            ::= { hwSiteStatus 11 }

        hwSiteMonitors OBJECT IDENTIFIER ::= { hwSiteMonitorMIBObjects 2 }

        hwMonitorsGroup OBJECT IDENTIFIER ::= { hwSiteMonitors 1 }

        hwMonsGroupId OBJECT-TYPE
            SYNTAX Unsigned32
            MAX-ACCESS read-only
            STATUS current
            DESCRIPTION
                "Site monitor group ID, is the unique ID of the site monitors."
            ::= { hwMonitorsGroup 1 }

        hwMonsGroupName OBJECT-TYPE
            SYNTAX OCTET STRING (SIZE (0..63))
            MAX-ACCESS read-write
            STATUS current
            DESCRIPTION
                "Site monitor group name is of the character string type, used to specify the monitor group. Users can configure it. Otherwise, the configured character can not be any other languages except English."
            ::= { hwMonitorsGroup 2 }

        hwMonsQuantity OBJECT-TYPE
            SYNTAX Unsigned32 (0..100)
            MAX-ACCESS read-only
            STATUS current
            DESCRIPTION
                "Total site intelligent monitors. Units:pcs."
            ::= { hwMonitorsGroup 3 }

        hwMonitor OBJECT IDENTIFIER ::= { hwSiteMonitors 2 }

        hwMonitorTable OBJECT-TYPE
            SYNTAX SEQUENCE OF HwMonitorEntry
            MAX-ACCESS not-accessible
             STATUS current
             DESCRIPTION
                "/"
            ::= { hwMonitor 1 }

        hwMonitorEntry OBJECT-TYPE
                        SYNTAX HwMonitorEntry
            MAX-ACCESS not-accessible
             STATUS current
             DESCRIPTION
                "/"
            INDEX { hwMonIndex }
            ::= { hwMonitorTable 1 }

        HwMonitorEntry            ::= SEQUENCE {
                hwMonIndex
                    Integer32,
                hwMonEquipId
                    Unsigned32,
                hwMonEquipName
                    OCTET STRING,
                hwMonEquipDescription
                    OCTET STRING,
                hwMonEquipSoftwareVersion
                    OCTET STRING,
                hwMonEquipPcbVersion
                    OCTET STRING,
                hwMonEquipManufacturer
                    OCTET STRING,
                hwMonEquipManuDate
                    OCTET STRING,
                hwMonEquipSerialNo
                    OCTET STRING,
                hwMonEquipOperTotalTime
                    Unsigned32,
                hwSetMonEquipCtrlState
                    INTEGER,
                hwCtrlMonEquipReset
                    INTEGER,
                hwMonitorOperStatus
                    INTEGER,
                hwMonRowStatus
                    RowStatus
            }

        hwMonIndex OBJECT-TYPE
            SYNTAX Integer32 (1..100)
            MAX-ACCESS read-only
            STATUS current
            DESCRIPTION
                "Table index of the site monitors (hwSiteMonitorTable) is restricted by the quantity of the site monitors (hwMonsQuantity). 
                Value range: 1 to 100."
            ::= { hwMonitorEntry 1 }

        hwMonEquipId OBJECT-TYPE
            SYNTAX Unsigned32
            MAX-ACCESS read-only
            STATUS current
            DESCRIPTION
                "Site monitor ID. 
                Value range: 001,001 to 001,100, in which the first three digits indicate the device type and the last three digits indicate the device SN. "
            ::= { hwMonitorEntry 2 }

        hwMonEquipName OBJECT-TYPE
            SYNTAX OCTET STRING (SIZE (0..63))
            MAX-ACCESS read-write
            STATUS current
            DESCRIPTION
                "Monitor name. It is of the character string type, and users can set the name of the monitor.   
                Otherwise, the configured character can not be any other languages except English."
            ::= { hwMonitorEntry 3 }

        hwMonEquipDescription OBJECT-TYPE
            SYNTAX OCTET STRING (SIZE (0..63))
            MAX-ACCESS read-write
            STATUS current
            DESCRIPTION
                "Monitor description. It is of the character string type. Users can set the description of the monitor. 
                 Otherwise, the configured character can not be any other languages except English."
            ::= { hwMonitorEntry 4 }

        hwMonEquipSoftwareVersion OBJECT-TYPE
            SYNTAX OCTET STRING (SIZE (0..63))
            MAX-ACCESS read-only
            STATUS current
            DESCRIPTION
                "Monitor software version. It is of the character string type."
            ::= { hwMonitorEntry 5 }

        hwMonEquipPcbVersion OBJECT-TYPE
            SYNTAX OCTET STRING (SIZE (0..63))
            MAX-ACCESS read-only
            STATUS current
            DESCRIPTION
                "Monitor printed circuit board (PCB) hardware version. It is of the character string type."
            ::= { hwMonitorEntry 6 }

        hwMonEquipManufacturer OBJECT-TYPE
            SYNTAX OCTET STRING (SIZE (0..63))
            MAX-ACCESS read-only
            STATUS current
            DESCRIPTION
                "Monitor manufacture. It is of the character string type, and is an inherent attribute of the device."
            ::= { hwMonitorEntry 7 }

        hwMonEquipManuDate OBJECT-TYPE
            SYNTAX OCTET STRING (SIZE (0..127))
            MAX-ACCESS read-only
            STATUS current
            DESCRIPTION
                "Monitor production date. It is of the character string type, and is an inherent attribute of the device.  "
            ::= { hwMonitorEntry 8 }

        hwMonEquipSerialNo OBJECT-TYPE
            SYNTAX OCTET STRING (SIZE (0..127))
            MAX-ACCESS read-only
            STATUS current
            DESCRIPTION
                "Production SN of the monitor. It is the electronic tag of the products."
            ::= { hwMonitorEntry 9 }

        hwMonEquipOperTotalTime OBJECT-TYPE
            SYNTAX Unsigned32 (0..65535)
            MAX-ACCESS read-only
            STATUS current
            DESCRIPTION
                "Total monitor runtime. The monitor counts the data in real time. 
                Value range is 0 to 65535,
                The value  is an integer (1), 
                Units:hours. (h). 
                It is used for performance measurement and evaluation of the monitor."
            ::= { hwMonitorEntry 10 }

        hwSetMonEquipCtrlState OBJECT-TYPE
            SYNTAX INTEGER
                {
                manualMode(1),
                autoMode(2),
                unknown(255)
                }
            MAX-ACCESS read-write
            STATUS current
            DESCRIPTION
                "Monitor control status. It is an enumeration type:
                  If the enumeration value is 1, it indicates the background control;
                  If the enumeration value is 2, it indicates the automatic control.
                  If the enumeration value is 255, it indicates monitor module operation status unknown. 
                  In manual state, monitor works under background commands; while monitors runs well automatically in auto state. 
                  For details, see the corresponding user manual of the monitor."
            ::= { hwMonitorEntry 11 }

        hwCtrlMonEquipReset OBJECT-TYPE
            SYNTAX INTEGER
                {
                normal(1),
                reset(2),
                unknown(255)
                }
            MAX-ACCESS read-write
            STATUS current
            DESCRIPTION
                "Warm-reset control of the monitor. It is an enumeration type:
                  If the enumeration value is 1, it indicates the Warm-reset control of the monitor is normal;
                  If the enumeration value is 2, it indicates the Warm-reset control of the monitor is reset.
                  If the enumeration value is 255, it indicates the Warm-reset control of the monito is unknown. "
            ::= { hwMonitorEntry 12 }

        hwMonitorOperStatus OBJECT-TYPE
            SYNTAX INTEGER
                {
                normal(1),
                commRs485Fail(2),
                commNetFail(3),
                fault(4),
                alarmResume(254),
                unknown(255)
                }
            MAX-ACCESS read-only
            STATUS current
            DESCRIPTION
                "State of the site monitor module. It is an enumeration type: 
                  If the enumeration value is 1, it indicates that the site monitor module is in the normal state;
                  If the enumeration value is 2, it indicates that the monitor module RS485 port communication failed; 
                  If the enumeration value is 3, it indicates that the monitor module net port communication failed;  
                  If the enumeration value is 4, it indicates that a fault occurs on the monitor module; 
                  If the enumeration value is 254, it indicates monitor module alarm resume;  
                  If the enumeration value is 255, it indicates monitor module operation status unknown. "
            ::= { hwMonitorEntry 99 }

        hwMonRowStatus OBJECT-TYPE
            SYNTAX RowStatus
            MAX-ACCESS read-create
            STATUS current
            DESCRIPTION
                "RowStatus of site monitor."
            ::= { hwMonitorEntry 100 }

        hwSiteRectifiers OBJECT IDENTIFIER ::= { hwSiteMonitorMIBObjects 3 }

        hwRectsGroup OBJECT IDENTIFIER ::= { hwSiteRectifiers 1 }

        hwRectsGroupId OBJECT-TYPE
            SYNTAX Unsigned32
            MAX-ACCESS read-only
            STATUS current
            DESCRIPTION
                "Device group ID of the rectifier module. It is the unique ID of the rectifier module group, and its default value: 002,000. 
                  The first digits indicate the device type and the last three digits indicate the device SN. If the last three digits are 000, it indicates a virtual device. "
            ::= { hwRectsGroup 1 }

        hwRectsGroupName OBJECT-TYPE
            SYNTAX OCTET STRING (SIZE (0..63))
            MAX-ACCESS read-write
            STATUS current
            DESCRIPTION
                "Name of the rectifier module group, character string type, is used to specify the rectifier module group. Users can configure it.  
                Otherwise, the configured character can not be any other languages except English."
            ::= { hwRectsGroup 2 }

        hwRectsTotalCurrent OBJECT-TYPE
            SYNTAX Unsigned32 (0..200000)
            MAX-ACCESS read-only
            STATUS current
            DESCRIPTION
                "Total current of the rectifier module group on the site. It indicates the real-time statistics of the rectifier module group on the site. 
                Default value: 0 to 20000, 
                units: A, 
                and the value is accurate to one decimal place (.1). 
                If the value is 2147483647(0x7FFFFFFF), it indicates that the value is invalid."
            ::= { hwRectsGroup 3 }

        hwRectsTotalQuantity OBJECT-TYPE
            SYNTAX Unsigned32 (0..256)
            MAX-ACCESS read-only
            STATUS current
            DESCRIPTION
                "Total quantity of the rectifier modules. 
                Value range: 0 to 256. Units:pcs."
            ::= { hwRectsGroup 4 }

        hwRectsRatedVoltage OBJECT-TYPE
            SYNTAX Unsigned32 (420..583)
            MAX-ACCESS read-only
            STATUS current
            DESCRIPTION
                "Rated voltage of the rectifier module group. It is an inherent attribute. 
                Value range: 42 to 58.3,
                Units: V, 
                and the value is accurate to one decimal place (.1). 
                 If the value is 2147483647(0x7FFFFFFF), it indicates that the value is invalid."
            ::= { hwRectsGroup 5 }

        hwModifyRectsOutputVoltage OBJECT-TYPE
            SYNTAX Unsigned32 (410..590)
            MAX-ACCESS read-write
            STATUS current
            DESCRIPTION
                "Voltage adjustment of the rectifier module, which users can configure it. 
                Value range: 41 to 59,
                Units: V, 
                and the value is accurate to one decimal space (.1). 
                Based on the actual requirements, users can modify the output voltage of the rectifier module by modifying the value of the node. 
                If the value is 2147483647(0x7FFFFFFF), it indicates that the value is invalid.
                NOTES: Be cautious about changing the value of the node.  Only the system in manual mode, this parameter can be configured successfully."
            ::= { hwRectsGroup 6 }

        hwSetRectsRedundEnable OBJECT-TYPE
            SYNTAX INTEGER
                {
                disable(1),
                enable(2),
                funcNotSupport(3)
                }
            MAX-ACCESS read-write
            STATUS current
            DESCRIPTION
                "Sleep function of the rectifier module group on the site. It is an enumeration value:
                If the NMS notifies the SNMP agent that this node is set to 1, it means to disable the sleep function of the rectifier module group;
                If the NMS notifies the SNMP agent that this node is set to 2, it means to enable the sleep function of the rectifier module group.
                If NMS get the node value is 3, it indicates that this function is not support, 
                and in such case the value set to the agent is invalid.
                Default value: to disable the sleep function of the rectifier module group. For details, see the corresponding user manual of the monitor."
            ::= { hwRectsGroup 7 }

        hwCtrlRectsAllOnOff OBJECT-TYPE
            SYNTAX INTEGER
                {
                on(1),
                off(2),
                nullOper(255)
                }
            MAX-ACCESS read-write
            STATUS current
            DESCRIPTION
                "Power-on or power-off of the rectifier module group (all the rectifier modules) on the site. It is an enumeration value:
                If the NMS notifies the SNMP agent that this node is set to 1, it indicates power-on of all rectifier modules;
                If the NMS notifies the SNMP agent that this node is set to 2, it indicates power-off of all the rectifier modules;
                If the NMS notifies the SNMP agent that this node is set to 255, it indicates nullOper of all the rectifier modules.
                NOTE: Only the system in manual mode, this parameter can be configured successfully."
            ::= { hwRectsGroup 8 }

        hwRectsTotalDCPower OBJECT-TYPE
            SYNTAX Unsigned32 (0..100000000)
            MAX-ACCESS read-only
            STATUS current
            DESCRIPTION
                "Total power of the direct current output.
                Value range: 0 to 100000000,
                units: W, 
                and the value is an integer.
                If the value is 2147483647(0x7FFFFFFF), it indicates that the value is invalid."
            ::= { hwRectsGroup 9 }

        hwRectsLoadUsage OBJECT-TYPE
            SYNTAX Unsigned32 (0..150)
            MAX-ACCESS read-only
            STATUS current
            DESCRIPTION
                "Load Usage.
                Value range: 0 to 150, 
                units: %, 
                and the value is an integer. 
                If the value is 2147483647(0x7FFFFFFF), it indicates that the value is invalid."
            ::= { hwRectsGroup 10 }

        hwRectsTotalACInputPower OBJECT-TYPE
            SYNTAX Unsigned32 (0..100000000)
            MAX-ACCESS read-only
            STATUS current
            DESCRIPTION
                "Total power of the direct current output. 
                Value range: 0 to 100000000, 
                units: W, 
                and the value is an integer. 
                If the value is 2147483647(0x7FFFFFFF), it indicates that the value is invalid."
            ::= { hwRectsGroup 11 }

        hwRectsHighRectifierCapacity OBJECT-TYPE
            SYNTAX Unsigned32 (0..150)
            MAX-ACCESS read-write
            STATUS current
            DESCRIPTION
                "High rectifier capacity. 
                Value range: 0 to 150, 
                units: %, 
                and the value is an integer. 
                If the value is 2147483647(0x7FFFFFFF), it indicates that the value is invalid."
            ::= { hwRectsGroup 12 }

        hwRectsLowRectifierCapacity OBJECT-TYPE
            SYNTAX Unsigned32 (0..150)
            MAX-ACCESS read-write
            STATUS current
            DESCRIPTION
                "Low rectifier capacity. 
                Value range: 0 to 150, 
                units: %, 
                and the value is an integer. 
                If the value is 2147483647(0x7FFFFFFF), it indicates that the value is invalid."
            ::= { hwRectsGroup 13 }

        hwRectsOverVoltProtThres OBJECT-TYPE
            SYNTAX Unsigned32 (560..605)
            MAX-ACCESS read-write
            STATUS current
            DESCRIPTION
                "Overvoltage protection threshold. 
                Value range: 56.0 to 60.5, 
                units: V, 
                and the value is accurate to one decimal space (.1). 
                If the value is 2147483647(0x7FFFFFFF), it indicates that the value is invalid."
            ::= { hwRectsGroup 14 }

        hwRectifier OBJECT IDENTIFIER ::= { hwSiteRectifiers 2 }

        hwRectConfigTable OBJECT-TYPE
            SYNTAX SEQUENCE OF HwRectConfigEntry
            MAX-ACCESS not-accessible
             STATUS current
             DESCRIPTION
                "Rectifier config information table. Use this table to get rectifiers equipment ID, software version, manufacturer, rated current, efficency, AC input type, and to control equipment on or off. 
                This table's index is hwRectConfigIndex, clone Rectifier config information table."
            ::= { hwRectifier 1 }

        hwRectConfigEntry OBJECT-TYPE
                        SYNTAX HwRectConfigEntry
            MAX-ACCESS not-accessible
             STATUS current
             DESCRIPTION
                "Rectifier config information table. Use this table to get rectifiers equipment ID, software version, manufacturer, rated current, efficency, AC input type, and to control equipment on or off. 
                This table's index is hwRectConfigIndex, clone Rectifier config information table."
            INDEX { hwRectConfigIndex }
            ::= { hwRectConfigTable 1 }

        HwRectConfigEntry            ::= SEQUENCE {
                hwRectConfigIndex
                    Integer32,
                hwRectEquipId
                    Unsigned32,
                hwRectEquipName
                    OCTET STRING,
                hwRectSoftwareVersion
                    OCTET STRING,
                hwRectSerialNo
                    OCTET STRING,
                hwRectRatedCurrent
                    Unsigned32,
                hwRectEfficency
                    Unsigned32,
                hwRectFatherEquipName
                    OCTET STRING
            }

        hwRectConfigIndex OBJECT-TYPE
            SYNTAX Integer32 (1..65535)
            MAX-ACCESS read-only
            STATUS current
            DESCRIPTION
                "Index of the device configuration list for the rectifier modules, which value range: 1 to 65535(To the actual subject). Lines of the device list are restricted by the total quantity of the rectifier modules (hwRectsTotalQuantity)."
            ::= { hwRectConfigEntry 1 }

        hwRectEquipId OBJECT-TYPE
            SYNTAX Unsigned32
            MAX-ACCESS read-only
            STATUS current
            DESCRIPTION
                "Rectifier module ID. Value range: 002'001 to 002'255. The first digits indicate the device type and last three digits indicate the device SN. "
            ::= { hwRectConfigEntry 2 }

        hwRectEquipName OBJECT-TYPE
            SYNTAX OCTET STRING (SIZE (0..63))
            MAX-ACCESS read-only
            STATUS current
            DESCRIPTION
                "Device name of the rectifier module, character string type, is used to specify the rectifier module. "
            ::= { hwRectConfigEntry 3 }

        hwRectSoftwareVersion OBJECT-TYPE
            SYNTAX OCTET STRING (SIZE (0..63))
            MAX-ACCESS read-only
            STATUS current
            DESCRIPTION
                "Software version of the rectifier module. It indicates the software version ID of the module. "
            ::= { hwRectConfigEntry 5 }

        hwRectSerialNo OBJECT-TYPE
            SYNTAX OCTET STRING (SIZE (0..127))
            MAX-ACCESS read-only
            STATUS current
            DESCRIPTION
                "Rectifier module SN. It indicates the electronic tag of the product."
            ::= { hwRectConfigEntry 8 }

        hwRectRatedCurrent OBJECT-TYPE
            SYNTAX Unsigned32 (0..2000)
            MAX-ACCESS read-only
            STATUS current
            DESCRIPTION
                "Rated voltage of the rectifier module, is an inherent attribute. 
                Value range: 0 to 200, Units: A, and the value is accurate to one decimal place (.1). If the value is 2147483647(0x7FFFFFFF), it indicates that the value is invalid. "
            ::= { hwRectConfigEntry 9 }

        hwRectEfficency OBJECT-TYPE
            SYNTAX Unsigned32 (0..100)
            MAX-ACCESS read-only
            STATUS current
            DESCRIPTION
                "Efficiency of the rectifier module, is an inherent attribute. 
                Value range: 0 to 100, 
                Units: %, 
                If the value is 2147483647(0x7FFFFFFF), it indicates that the value is invalid."
            ::= { hwRectConfigEntry 10 }

        hwRectFatherEquipName OBJECT-TYPE
            SYNTAX OCTET STRING
            MAX-ACCESS read-only
            STATUS current
            DESCRIPTION
                "Name of the parent device of the Rectifier"
            ::= { hwRectConfigEntry 14 }

        hwRectOperTable OBJECT-TYPE
            SYNTAX SEQUENCE OF HwRectOperEntry
            MAX-ACCESS not-accessible
             STATUS current
             DESCRIPTION
                "Rectifier runing information table. Use this table to get rectifiers output current, output voltage, totle runing time, and current run status. 
                This table's index is hwRectRunIndex, clone rectifier runing information table."
            ::= { hwRectifier 2 }

        hwRectOperEntry OBJECT-TYPE
                        SYNTAX HwRectOperEntry
            MAX-ACCESS not-accessible
             STATUS current
             DESCRIPTION
                "Rectifier runing information table. Use this table to get rectifiers output current, output voltage, totle runing time, and current run status. 
                This table's index is hwRectRunIndex, clone rectifier runing information table."
            INDEX { hwRectOperIndex }
            ::= { hwRectOperTable 1 }

        HwRectOperEntry            ::= SEQUENCE {
                hwRectOperIndex
                    Integer32,
                hwRectOutputCurrent
                    Unsigned32,
                hwRectOutputVoltage
                    Unsigned32,
                hwRectDCOutputPower
                    Unsigned32,
                hwRectACVoltage
                    Unsigned32,
                hwRectRatedEfficiency
                    Unsigned32,
                hwRectifierTemperature
                    Integer32,
                hwRectOperStatus
                    INTEGER,
                hwRectOperRowStatus
                    RowStatus
            }

        hwRectOperIndex OBJECT-TYPE
            SYNTAX Integer32 (1..65535)
            MAX-ACCESS read-only
            STATUS current
            DESCRIPTION
                "Table index of the running rectifier modules, 
                which value range: 1 to 65535(To the actual subject). 
                Lines of the device list are restricted by the total quantity of the rectifier modules (hwRectsTotalQuantity)."
            ::= { hwRectOperEntry 1 }

        hwRectOutputCurrent OBJECT-TYPE
            SYNTAX Unsigned32 (0..3000)
            MAX-ACCESS read-only
            STATUS current
            DESCRIPTION
                "Output current of the rectifier module. It is a real-time analog parameter. 
                Value range: 0 to 300, 
                Units: A, 
                and the value is accurate to one decimal place (.1). 
                If the value is 2147483647(0x7FFFFFFF), it indicates that the value is invalid."
            ::= { hwRectOperEntry 2 }

        hwRectOutputVoltage OBJECT-TYPE
            SYNTAX Unsigned32 (0..1000)
            MAX-ACCESS read-only
            STATUS current
            DESCRIPTION
                "Output voltage of the rectifier module. It is a real-time analog parameter. 
                Value range: 0 to 100, 
                Units: V, 
                the value is accurate to one decimal place (.1). 
                If the value is 2147483647(0x7FFFFFFF), it indicates that the value is invalid. "
            ::= { hwRectOperEntry 3 }

        hwRectDCOutputPower OBJECT-TYPE
            SYNTAX Unsigned32 (0..30000)
            MAX-ACCESS read-only
            STATUS current
            DESCRIPTION
                "DC output power. 
                Value range: 0 to 30000, 
                units: W, 
                and the value is an integer (1).  
                If the value is 2147483647(0x7FFFFFFF), it indicates that the value is invalid."
            ::= { hwRectOperEntry 5 }

        hwRectACVoltage OBJECT-TYPE
            SYNTAX Unsigned32 (0..6000)
            MAX-ACCESS read-only
            STATUS current
            DESCRIPTION
                "AC input voltage. 
                Value range: 0 to 600, 
                units: V, 
                and the value is accurate to one decimal space (.1).
                If the value is 2147483647(0x7FFFFFFF), it indicates that the value is invalid."
            ::= { hwRectOperEntry 6 }

        hwRectRatedEfficiency OBJECT-TYPE
            SYNTAX Unsigned32 (0..100)
            MAX-ACCESS read-only
            STATUS current
            DESCRIPTION
                "Rated Efficiency. 
                Value range: 0 to 100, 
                units: %, 
                and the value is an integer.(1). 
                If the value is 2147483647(0x7FFFFFFF), it indicates that the value is invalid."
            ::= { hwRectOperEntry 7 }

        hwRectifierTemperature OBJECT-TYPE
            SYNTAX Integer32 (-3000..3000)
            MAX-ACCESS read-only
            STATUS current
            DESCRIPTION
                "Rectifier Temperature. 
                Value range: -300 to 300, 
                units: degC, 
                and the value is accurate to one decimal space (.1). 
                If the value is 2147483647(0x7FFFFFFF), it indicates that the value is invalid."
            ::= { hwRectOperEntry 8 }

        hwRectOperStatus OBJECT-TYPE
            SYNTAX INTEGER
                {
                normal(1),
                fault(2),
                protect(3),
                commFail(4),
                switchOff(5),
                invalid(6),
                noConfig(7),
                acOff(8),
                rectLost(9),
                alarmResume(254),
                unknown(255)
                }
            MAX-ACCESS read-only
            STATUS current
            DESCRIPTION
                "State of the rectifier module. It is an enumeration type: 
                  If the enumeration value is 1, the rectifier module is in the normal state;
                  If the enumeration value is 2, a fault occurs on the rectifier module; 
                  If the enumeration value is 3, automatic protection of the rectifier module;
                  If the enumeration value is 4, communication of the rectifier module fails;
                  If the enumeration value is 5, the rectifier module is shut down; 
                  If the enumeration value is 6, the rectifier module is invalid; 
                  If the enumeration value is 7, this rectifier is not configured; 
                If the enumeration value is 8, this rectifier is ac off;
                If the enumeration value is 9, this rectifier is rectLost;
                  If the enumeration value is 254, rectifier alarm resume; 
                  If the enumeration value is 255, rectifier operation status unknown."
            ::= { hwRectOperEntry 99 }

        hwRectOperRowStatus OBJECT-TYPE
            SYNTAX RowStatus
            MAX-ACCESS read-create
            STATUS current
            DESCRIPTION
                "RowStatus of rectifier runing table."
            ::= { hwRectOperEntry 100 }

        hwSiteBatterys OBJECT IDENTIFIER ::= { hwSiteMonitorMIBObjects 4 }

        hwBattsConfig OBJECT IDENTIFIER ::= { hwSiteBatterys 1 }

        hwBattsGroupId OBJECT-TYPE
            SYNTAX Unsigned32
            MAX-ACCESS read-only
            STATUS current
            DESCRIPTION
                "Battery group ID. It is the unique ID of the battery group device. 
                The first digits indicate the device type and the last three digits indicate the device SN. 
                If the last three digits are 000, it indicates a virtual device. "
            ::= { hwBattsConfig 1 }

        hwBattsGroupName OBJECT-TYPE
            SYNTAX OCTET STRING (SIZE (0..63))
            MAX-ACCESS read-write
            STATUS current
            DESCRIPTION
                "Device name of the battery group. It is of the character string type, which can be configured by users. 
                Otherwise, the configured character can not be any other languages except English."
            ::= { hwBattsConfig 2 }

        hwBattsTotalQuantity OBJECT-TYPE
            SYNTAX Unsigned32 (0..100)
            MAX-ACCESS read-only
            STATUS current
            DESCRIPTION
                "Total quantity of battery strings, 
                which value range: 0 to 100. 
                Units:strings."
            ::= { hwBattsConfig 3 }

        hwSetBattsHighTempAction OBJECT-TYPE
            SYNTAX INTEGER
                {
                blvd(1),
                lowerDcOutput(2),
                disable(255)
                }
            MAX-ACCESS read-write
            STATUS current
            DESCRIPTION
                "Battery high-temperature protection mode. It is an enumeration value, and can be configured. 
                If the enumeration value is 1, it indicates the power-off protection mode;
                If the enumeration value is 2, it indicates the protection mode of lowering the output voltage of the rectifier module. 
                If the enumeration value is 255, it indicates do nothing. "
            ::= { hwBattsConfig 4 }

        hwSetBattsHighTempVoltLimit OBJECT-TYPE
            SYNTAX Unsigned32 (420..530)
            MAX-ACCESS read-write
            STATUS current
            DESCRIPTION
                "Battery protection voltage under high temperature. It works with the low-voltage power-off protection in battery high-temperature protection mode, which can be configured by users. 
                If the low-voltage power-off protection mode (that is, the enumeration value is 1) is selected, the node is a low-voltage power-off node. 
                Value range: 42 to 53, 
                units: V, 
                and the value is accurate to one decimal place (.1).  
                If the value is 2147483647(0x7FFFFFFF), it indicates that the value is invalid."
            ::= { hwBattsConfig 5 }

        hwSetBattsHTDLimit OBJECT-TYPE
            SYNTAX Integer32 (25..80)
            MAX-ACCESS read-write
            STATUS current
            DESCRIPTION
                "Upper threshold of the battery high temperature disconnection(HTD), can be configured by users. 
                Value range: 25 to 80, 
                Units: centigrade (degC), 
                and the value is an integer (1). 
                If the value is 2147483647(0x7FFFFFFF), it indicates that the value is invalid.
                NOTE: There is linkage between hwSetBattsHTDLimit and hwSetBattsTempUpperLimit"
            ::= { hwBattsConfig 6 }

        hwSetBattsHTDEnable OBJECT-TYPE
            SYNTAX INTEGER
                {
                enable(1),
                disable(2)
                }
            MAX-ACCESS read-write
            STATUS current
            DESCRIPTION
                "Battery high temperature disconnection enable. It is an enumeration type:
                  If the enumeration value is 1, enable the operation of the battery disconnection in high temperature; 
                  If the enumeration value is 2, disable the operation of the battery disconnection in high temperature. 
                  The operation of the battery disconnection in high temperature is disabled by default. "
            ::= { hwBattsConfig 7 }

        hwSetBattsFloatVoltage OBJECT-TYPE
            SYNTAX Unsigned32 (420..583)
            MAX-ACCESS read-write
            STATUS current
            DESCRIPTION
                "Float charge voltage of the batteries, can be configured by users. 
                Value range: 42 to 58.3, 
                units: V, 
                and the value is accurate to one decimal place (.1) 
                If the value is 2147483647(0x7FFFFFFF), it indicates that the value is invalid.
                NOTE: There is linkage between hwSetBattsFloatVoltage and hwSetBattsBoostVoltage
                "
            ::= { hwBattsConfig 8 }

        hwSetBattsBoostVoltage OBJECT-TYPE
            SYNTAX Unsigned32 (420..583)
            MAX-ACCESS read-write
            STATUS current
            DESCRIPTION
                "Boostcharge voltage of the batteries, can be configured by users. 
                Value range: 42 to 58.3, 
                units: V, 
                and the value is accurate to one decimal place (.1). 
                If the value is 2147483647(0x7FFFFFFF), it indicates that the value is invalid.
                NOTE: There is linkage between hwSetBattsFloatVoltage and hwSetBattsBoostVoltage"
            ::= { hwBattsConfig 9 }

        hwSetBattsCurrLimitCoefficient OBJECT-TYPE
            SYNTAX Unsigned32 (5..50)
            MAX-ACCESS read-write
            STATUS current
            DESCRIPTION
                "Current-limiting point coefficient of the batteries, can be configured by users. 
                Value range: 0.05 to 0.5, 
                units: C10, 
                and the value is accurate to two decimal places (.01). 
                If the value is 2147483647(0x7FFFFFFF), it indicates that the value is invalid.
                There is linkage between  hwSetBattsChargeOvercurAlmThreshold and  hwSetBattsCurrLimitCoefficient.
                Current-limiting point coefficient must be less than or equal to the charge overcurrent alarm threshold."
            ::= { hwBattsConfig 10 }

        hwSetBattsCompFactor OBJECT-TYPE
            SYNTAX Unsigned32 (0..500)
            MAX-ACCESS read-write
            STATUS current
            DESCRIPTION
                "Temperature compensated coefficient of the batteries, can be configured by user. 
                Value range: 0 to 500, 
                units: mv per centigrade, 
                and the value is an integer (1). 
                If the value is 2147483647(0x7FFFFFFF), it indicates that the value is invalid."
            ::= { hwBattsConfig 11 }

        hwCtrlBattsBoostFloat OBJECT-TYPE
            SYNTAX INTEGER
                {
                floatCharge(1),
                boostCharge(2),
                nullOper(255)
                }
            MAX-ACCESS read-write
            STATUS current
            DESCRIPTION
                "Control batteries charge mode between boost and float. It is an enumeration value. 
                  Users actively control the conversion. 
                  If the NMS notifies the SNMP agent that this node is set to 1, it means to start the float charge mode of the batteries; 
                  If the NMS notifies the SNMP agent that this node is set to 2, it means to start the boost charge mode of the batteries. 
                  If the NMS notifies the SNMP agent that this node is set to 255, it means to start the mode of the batteries is nullOper. "
            ::= { hwBattsConfig 12 }

        hwSetBattsRatedCapacity OBJECT-TYPE
            SYNTAX Unsigned32 (5..10000)
            MAX-ACCESS read-write
            STATUS current
            DESCRIPTION
                "Set batteries rated capacity. It is an analog parameter collected by the battery string in real time.
                Value range: 5 to 10000, 
                units: Ah, 
                the value is an integer (1). 
                If the value is 2147483647(0x7FFFFFFF), it indicates that the value is invalid."
            ::= { hwBattsConfig 13 }

        hwSetBattsTimedBoostChargeEnabled OBJECT-TYPE
            SYNTAX INTEGER
                {
                disable(1),enable(2),unknown(255)
                }
            MAX-ACCESS read-write
            STATUS current
            DESCRIPTION
                "Timed Boost Charge Enabled. It is an enumeration value, and can be configured. 
                If the enumeration value is 1, it indicates timed boost charge is disabled;
                If the enumeration value is 2, it indicates timed boost charge is enabled. 
                If the enumeration value is 255, it indicates timed boost charge is unknown. "
            ::= { hwBattsConfig 14 }

        hwSetBattsTimedBoostChargePeriod OBJECT-TYPE
            SYNTAX Unsigned32 (1..365)
            MAX-ACCESS read-write
            STATUS current
            DESCRIPTION
                "Timed Boost Charge Interval. 
                Value range: 1 to 365, 
                units: Day, 
                and the value is an integer. 
                If the value is 2147483647(0x7FFFFFFF), it indicates that the value is invalid."
            ::= { hwBattsConfig 15 }

        hwSetBattsMaxTimedBCDuration OBJECT-TYPE
            SYNTAX Unsigned32 (1..24)
            MAX-ACCESS read-write
            STATUS current
            DESCRIPTION
                "Maximum Timed Boost Charge Duration. 
                Value range: 1 to 24, 
                units: h, 
                and the value is an integer.(1). 
                If the value is 2147483647(0x7FFFFFFF), it indicates that the value is invalid."
            ::= { hwBattsConfig 16 }

        hwSetBattsChargeOvercurAlmThreshold OBJECT-TYPE
            SYNTAX Unsigned32 (5..100)
            MAX-ACCESS read-write
            STATUS current
            DESCRIPTION
                "Charge Overcurrent Alarm Threshold. 
                Value range: 0.05 to 1, 
                units: C10, 
                and the value is accurate to two decimal space (.01). 
                If the value is 2147483647(0x7FFFFFFF), it indicates that the value is invalid.
                There is linkage between  hwSetBattsChargeOvercurAlmThreshold and  hwSetBattsCurrLimitCoefficient.
                Current-limiting point coefficient must be less than or equal to the charge overcurrent alarm threshold."
            ::= { hwBattsConfig 17 }

        hwSetBattsLowCapacityAlarmThreshold OBJECT-TYPE
            SYNTAX Unsigned32 (0..90)
            MAX-ACCESS read-write
            STATUS current
            DESCRIPTION
                "Low Capacity Alarm Threshold. 
                Value range: 0 to 90, 
                units: %, 
                and the value is an integer. (1)
                If the value is 2147483647(0x7FFFFFFF), it indicates that the value is invalid."
            ::= { hwBattsConfig 18 }

        hwBattsOperate OBJECT IDENTIFIER ::= { hwSiteBatterys 2 }

        hwBattsTotalCurrent OBJECT-TYPE
            SYNTAX Integer32 ( -4000000..4000000)
            MAX-ACCESS read-only
            STATUS current
            DESCRIPTION
                "Total current of the battery group. It indicates the real-time statistics of the battery group on the site. 
                Value range: -400000 to +400000, 
                units: A, 
                and the value is accurate to one decimal place (.1).  
                If the value is 2147483647(0x7FFFFFFF), it indicates that the value is invalid."
            ::= { hwBattsOperate 1 }

        hwBattsPreDischargeTime OBJECT-TYPE
            SYNTAX Unsigned32 (0..15360)
            MAX-ACCESS read-only
            STATUS current
            DESCRIPTION
                "Battery group backup time. It indicates the real-time statistics of the battery group. 
                Value range: 0 to 15360, 
                Units: minutes (min),  
                and the value is an integer (1).  
                If the value is 2147483647(0x7FFFFFFF), it indicates that the value is invalid."
            ::= { hwBattsOperate 2 }

        hwBattsChargeStatus OBJECT-TYPE
            SYNTAX INTEGER
                {
                floatCharge(1),
                boostCharge(2),
                disCharge(3),
                hibernating(4),
                offline(7),
                unknown(255)
                }
            MAX-ACCESS read-only
            STATUS current
            DESCRIPTION
                "Battery charging state, indicates the charging and discharging information about the battery group. It is an enumeration type. 
                If the enumeration value is 1, it indicates a battery group in the float charging state. 
                If the enumeration value is 2, it indicates a battery group in the boost charging state. 
                If the enumeration value is 3, it indicates a battery group in the discharging state. 
                If the enumeration value is 4, it indicates a battery group in the hibernating state.
                If the enumeration value is 7, it indicates a battery group in the Offline state.
                If the enumeration value is 255, it indicates a battery group in the Offline state. "
            ::= { hwBattsOperate 3 }

        hwBattsCurrLimitStatus OBJECT-TYPE
            SYNTAX INTEGER
                {
                unlimited(1),
                limited(2),
                unknown(255)
                }
            MAX-ACCESS read-only
            STATUS current
            DESCRIPTION
                "Battery group current-limiting state, indicates the state information about the battery group. It is an enumeration value. 
                  If the enumeration value is 1, it indicates that the current of the battery group is not limited. 
                  If the enumeration value is 2, it indicates the current of the battery group is limited.
                  If the enumeration value is 255, it indicates the current of the battery group is unknown. "
            ::= { hwBattsOperate 4 }

        hwBattsTemprature1 OBJECT-TYPE
            SYNTAX Integer32 ( -300..200)
            MAX-ACCESS read-only
            STATUS current
            DESCRIPTION
                "Battery temperature. It is a battery parameter collected in real time. 
                Value range: -300 to 200, 
                unit: centigrade (degC), 
                and the value is an integer .
                If the value is 2147483647(0x7FFFFFFF), it indicates that battery temperature sensor is not configured."
            ::= { hwBattsOperate 5 }

        hwBattsTemprature2 OBJECT-TYPE
            SYNTAX Integer32 ( -50..100)
            MAX-ACCESS read-only
            STATUS current
            DESCRIPTION
                "Battery temperature. It is a battery parameter collected in real time. 
                Value range: -50 to +100, 
                unit: centigrade (degC), 
                and the value is an integer (1).
                If the value is 2147483647(0x7FFFFFFF), it indicates that battery temperature sensor is not configured."
            ::= { hwBattsOperate 6 }

        hwBattsAlarmsClear OBJECT-TYPE
            SYNTAX INTEGER
                {
                clearBattTestFailAlm(1),
                clearBattTestCanceledAlm(2),
                clearHighStrImpedanceAlm(3),
                clearHighFloatCurrAlm(4),
                clearCurrImbalanceAlm(5),
                clearContactorFaultAlm(6),
                nullOper(255)
                }
            MAX-ACCESS read-write
            STATUS current
            DESCRIPTION
                "Battery alarms clear. It is an enumeration type:
                  If the enumeration value is 1, it indicates the clear batt test fail alarm ;
                  If the enumeration value is 2, it indicates the clear batt test canceled alarm .
                  If the enumeration value is 3, it indicates the clear high str impedance alarm .
                  If the enumeration value is 4, it indicates the clear high float current alarm .
                  If the enumeration value is 5, it indicates the clear current imbalance alarm .
                  If the enumeration value is 6, it indicates the clear contactor fault alarm .
                  If the enumeration value is 255, it indicates null oper(can't set to smu)."
            ::= { hwBattsOperate 7 }

        hwBattsRatedCapacity OBJECT-TYPE
            SYNTAX Unsigned32 (0..2147483647)
            MAX-ACCESS read-only
            STATUS current
            DESCRIPTION
                "Batteries actual capacity. 
                It is an analog parameter collected by the battery string in real time.
                Value range: 0 to 2147483647, 
                units: Ah, 
                the value is an integer (1).  
                If the value is 2147483647(0x7FFFFFFF), it indicates that the value is invalid."
            ::= { hwBattsOperate 8 }

        hwBattsRemainCapacity OBJECT-TYPE
            SYNTAX Unsigned32 (0..2147483647)
            MAX-ACCESS read-only
            STATUS current
            DESCRIPTION
                "Remaining capacity of all of the battery. 
                It is an analog parameter collected by the battery string in real time. 
                Value range: 0 to 2147483647, 
                units: Ah, 
                and the value is an integer (1).  
                If the value is 2147483647(0x7FFFFFFF), it indicates that the value is invalid."
            ::= { hwBattsOperate 9 }

        hwTotalRemainingCapacityPercent OBJECT-TYPE
            SYNTAX Unsigned32 (0..100)
            MAX-ACCESS read-only
            STATUS current
            DESCRIPTION
                "Total Remaining Capacity Percent. 
                Value range: 0 to 100, units: %, 
                and the value is an integer.(1). 
                If the value is 2147483647(0x7FFFFFFF), it indicates that the value is invalid."
            ::= { hwBattsOperate 10 }

        hwBattsTotalDischargeDepth OBJECT-TYPE
            SYNTAX Unsigned32 (0..100)
            MAX-ACCESS read-only
            STATUS current
            DESCRIPTION
                "Battery Total Discharge Depth Percent. Value range: 0 to 100, units: %, and the value is an integer. If the value is 2147483647(0x7FFFFFFF), it indicates that the value is invalid."
            ::= { hwBattsOperate 11 }

        hwBattsTest OBJECT IDENTIFIER ::= { hwSiteBatterys 3 }

        hwBattsTestRecordCount OBJECT-TYPE
            SYNTAX Unsigned32 (0..100)
            MAX-ACCESS read-only
            STATUS current
            DESCRIPTION
                "Battery test records number."
            ::= { hwBattsTest 1 }

        hwSetBattsManuStdTestTime OBJECT-TYPE
            SYNTAX Unsigned32 (1..6000)
            MAX-ACCESS read-write
            STATUS current
            DESCRIPTION
                "Battery standard test time, It can be configured by users,
                value range defines between 1 to 6000, 
                units: minutes(min).  
                and its value is an integer (1). 
                Here, if battery manual test is standard mode, 
                If the value is 2147483647(0x7FFFFFFF), it indicates that the value is invalid."
            ::= { hwBattsTest 2 }

        hwSetBattsManuStdTestEndVolt OBJECT-TYPE
            SYNTAX Unsigned32 (170..220)
            MAX-ACCESS read-write
            STATUS current
            DESCRIPTION
                "Test end voltage of single battery, which can be configured by users.
                value range defines between 1.7 to 2.2
                Units: V/cell, 
                and the value is accurate to two decimal place (.01).  
                Here, if battery manual test is standard mode, . If the value is 2147483647(0x7FFFFFFF), it indicates that the value is invalid."
            ::= { hwBattsTest 3 }

        hwSetBattsManuStdTestCellNum OBJECT-TYPE
            SYNTAX Unsigned32 (1..50)
            MAX-ACCESS read-write
            STATUS current
            DESCRIPTION
                "Battery cell number in each Group, which is used in the battery standard manual test, can be configured by users. 
                Units: psc or cell, 
                value range defines between 1 to 50. 
                and value is an integer (1)."
            ::= { hwBattsTest 4 }

        hwSetBattsManuShortTestTime OBJECT-TYPE
            SYNTAX Unsigned32 (1..240)
            MAX-ACCESS read-write
            STATUS current
            DESCRIPTION
                "Battery short test time, It can be configured by users,
                value range defines between 1 to 240,  
                units: minutes(min).
                and its value is an integer (1).
                If battery manual test is simple mode,  
                If the value is 2147483647(0x7FFFFFFF), it indicates that the value is invalid."
            ::= { hwBattsTest 5 }

        hwSetBattsManuShortTestEndVolt OBJECT-TYPE
            SYNTAX Unsigned32 (442..530)
            MAX-ACCESS read-write
            STATUS current
            DESCRIPTION
                "Voltage when the battery short test is ended, can be configured by users. Here, if battery manual test is standard mode, 
                value range defines between 44.2 to 53, 
                Units: V, 
                and the value is accurate to one decimal place (.1). 
                If the value is 2147483647(0x7FFFFFFF), it indicates that the value is invalid."
            ::= { hwBattsTest 6 }

        hwCtrlBattsTestStartStop OBJECT-TYPE
            SYNTAX INTEGER
                {
                stdTestStart(1),
                shortTestStart(2),
                testStop(3),
                nullOper(255)
                }
            MAX-ACCESS read-write
            STATUS current
            DESCRIPTION
                "Battery manualtest start and stop. It is an enumeration value. 
                  If the value is 1, it means to start a standard manual test; 
                  If the value is 2, it means to start a short manual test; 
                  If the value is 3, it means to stop the battery test.
                If the value is 255, it means null operate(can't set to smu);  
                  Set the parameters, such as battery test time, and voltage when the battery test stops before the node controls the start of the battery test. If the parameters are not set this time, the system uses the configuration parameters by default; and if the battery test is started at the first time, the system uses the default value. 
                  Battery test can only start up in some conditions, so that the reason of Start of battery short test failed may be as follow:
                  1. Interval between this test and the latest AC outage or test is longer than the preset duration.
                  2. No major alarm is raised.
                  3. The number of healthy modules is greater than 0.
                  4. The number of battery strings is greater than 0."
            ::= { hwBattsTest 7 }

        hwBattsTestResultTable OBJECT-TYPE
            SYNTAX SEQUENCE OF HwBattsTestResultEntry
            MAX-ACCESS not-accessible
             STATUS current
             DESCRIPTION
                "Battery test result record table. 
                Use this table to get battery test inital time, test result, battery efficiency, battery discharge time, terminated voltage, average current, discharge AH value, test temperature and test terminated course. 
                This table's index is hwBattsTestResultIndex, clone Battery test result record table."
            ::= { hwBattsTest 100 }

        hwBattsTestResultEntry OBJECT-TYPE
                        SYNTAX HwBattsTestResultEntry
            MAX-ACCESS not-accessible
             STATUS current
             DESCRIPTION
                "Battery test result record table. 
                Use this table to get battery test inital time, test result, battery efficiency, battery discharge time, terminated voltage, average current, discharge AH value, test temperature and test terminated course. 
                This table's index is hwBattsTestResultIndex, clone Battery test result record table."
            INDEX { hwBattsTestResultIndex }
            ::= { hwBattsTestResultTable 1 }

        HwBattsTestResultEntry            ::= SEQUENCE {
                hwBattsTestResultIndex
                    Integer32,
                hwBattsTestType
                    INTEGER,
                hwBattsTestStartTime
                    OCTET STRING,
                hwBattsTestResult
                    INTEGER,
                hwBattsEfficiency
                    Integer32,
                hwBattsDischargeTime
                    Unsigned32,
                hwBattsDischargeEndVoltage
                    Unsigned32,
                hwBattsDischargeAvCurrent
                    Integer32,
                hwBattsDischargeAhValue
                    Unsigned32,
                hwBattsTestTemperature
                    Integer32,
                hwBattsTestEndCourse
                    INTEGER,
                hwBattsTestResultRowStatus
                    RowStatus
            }

        hwBattsTestResultIndex OBJECT-TYPE
            SYNTAX Integer32 (1..100)
            MAX-ACCESS read-only
            STATUS current
            DESCRIPTION
                "Table index of the battery test results. Currently up to 10 times of the battery test results are saved by default. "
            ::= { hwBattsTestResultEntry 1 }

        hwBattsTestType OBJECT-TYPE
            SYNTAX INTEGER
                {
                manualTest(1),
                acOffAutoTest(2),
                timedTest(3),
                shortTest(4),
                unknown(255)
                }
            MAX-ACCESS read-only
            STATUS current
            DESCRIPTION
                "Record test type of the battery test. It is an enumeration value: 
                  If the NMS notifies the SNMP agent that this node is set to 1, it indicates a manual test; 
                  If the NMS notifies the SNMP agent that this node is set to 2, it indicates a simplified test;
                  If the NMS notifies the SNMP agent that this node is set to 3, it indicates a timed test;
                  If the NMS notifies the SNMP agent that this node is set to 4, it indicates a short test;
                  If the NMS notifies the SNMP agent that this node is set to 255, it indicates a other test."
            ::= { hwBattsTestResultEntry 2 }

        hwBattsTestStartTime OBJECT-TYPE
            SYNTAX OCTET STRING (SIZE (0..127))
            MAX-ACCESS read-only
            STATUS current
            DESCRIPTION
                "Test start time of the record in the battery test. It is of the character string type."
            ::= { hwBattsTestResultEntry 3 }

        hwBattsTestResult OBJECT-TYPE
            SYNTAX INTEGER
                {
                battNoResult(1),
                battNormal(2),
                battPreAlarm(3),
                battAlarm(4),
                unknown(255)
                }
            MAX-ACCESS read-only
            STATUS current
            DESCRIPTION
                "Battery test result. It is an enumeration value.
                  If the enumeration value of the node is 1, it indicates that the battery test has no result: 
                  If the enumeration value of the node is 2, it indicates that the battery is in the normal state: 
                  If the enumeration value of the node is 3, it indicates that the battery is in the minor abnormal state, 
                  If the enumeration value of the node is 4, it indicates that the battery is in the alarm state,
                  If the enumeration value of the node is 255, it indicates that the battery state is unknown,"
            ::= { hwBattsTestResultEntry 4 }

        hwBattsEfficiency OBJECT-TYPE
            SYNTAX Integer32 (0..100)
            MAX-ACCESS read-only
            STATUS current
            DESCRIPTION
                "Battery efficiency test. 
                Value range: 0 to 100, 
                Units: %, 
                and the value is an integer (1).
                  If the value is -1, it indicates that the test value is inefficient.
                  If the value is 255, it indicates that the test value is invalid."
            ::= { hwBattsTestResultEntry 5 }

        hwBattsDischargeTime OBJECT-TYPE
            SYNTAX Unsigned32 (0..10000)
            MAX-ACCESS read-only
            STATUS current
            DESCRIPTION
                "Discharge time of the battery test records. 
                Value range: 0 to 100, 
                units: hour (h), 
                and the value is accurate to two decimal places (.01).  
                If the value is 2147483647(0x7FFFFFFF), it indicates that the value is invalid."
            ::= { hwBattsTestResultEntry 6 }

        hwBattsDischargeEndVoltage OBJECT-TYPE
            SYNTAX Unsigned32 (0..600)
            MAX-ACCESS read-only
            STATUS current
            DESCRIPTION
                "Discharge termination voltage of the battery test. 
                Value range: 0 to 60, 
                units: V, 
                and the value is accurate to one decimal place (.1).  
                If the value is 2147483647(0x7FFFFFFF), it indicates that the value is invalid."
            ::= { hwBattsTestResultEntry 7 }

        hwBattsDischargeAvCurrent OBJECT-TYPE
            SYNTAX Integer32 ( -10000..10000)
            MAX-ACCESS read-only
            STATUS current
            DESCRIPTION
                "Average discharge current of the battery test. 
                Value range: -1000 to 1000, 
                units: A, 
                and the value is accurate to one decimal place (.1).  
                If the value is 2147483647(0x7FFFFFFF), it indicates that the value is invalid."
            ::= { hwBattsTestResultEntry 8 }

        hwBattsDischargeAhValue OBJECT-TYPE
            SYNTAX Unsigned32 (0..5000)
            MAX-ACCESS read-only
            STATUS current
            DESCRIPTION
                "Discharge ampere per hour the battery test. 
                Value range: 0 to 5000, 
                Units: Ah, 
                and the value is an integer (1).   
                If the value is 2147483647(0x7FFFFFFF), it indicates that the value is invalid."
            ::= { hwBattsTestResultEntry 9 }

        hwBattsTestTemperature OBJECT-TYPE
            SYNTAX Integer32 ( -50..100)
            MAX-ACCESS read-only
            STATUS current
            DESCRIPTION
                "Battery temperature of the battery test termination. 
                Value range: -50 to +100, 
                Units: centigrade (degC), 
                and the value is an integer (1). 
                If the value is -1024, it indicates that no battery temperature value sensor is detected."
            ::= { hwBattsTestResultEntry 10 }

        hwBattsTestEndCourse OBJECT-TYPE
            SYNTAX INTEGER
                {
                voltageToEnd(1),
                timeToEnd(2),
                acOnToEnd(3),
                manulToEnd(4),
                faultAlarmToEnd(5),
                lowCapacityToEnd(6),
                lowTempToEnd(7),
                unknown(255)
                }
            MAX-ACCESS read-only
            STATUS current
            DESCRIPTION
                "Termination factors of the battery test. It is an enumeration value. 
                  If the enumeration value is 1, it indicates that the voltage value of the battery test reaches the set termination voltage; 
                  If the enumeration value is 2, it indicates that the voltage value of the battery test reaches the timing limit; 
                  If the enumeration value is 3, it indicates that an alarm related to the battery leads to the stop of the battery test; 
                  If the enumeration value is 4, it indicates that a battery test is stopped manually,
                  If the enumeration value is 5, it indicates that battery fault alarm happened,
                If the enumeration value is 6, it indicates that battery low capacity happened,
                If the enumeration value is 7, it indicates that battery low temp happened,
                  If the enumeration value is 255, it indicates that battery test end for other courses."
            ::= { hwBattsTestResultEntry 11 }

        hwBattsTestResultRowStatus OBJECT-TYPE
            SYNTAX RowStatus
            MAX-ACCESS read-create
            STATUS current
            DESCRIPTION
                "RowStatus of battery test table."
            ::= { hwBattsTestResultEntry 100 }

        hwSetBattsConsCurrTestEnable OBJECT-TYPE
            SYNTAX INTEGER
                {
                disable(1),
                enable(2)
                }
            MAX-ACCESS read-write
            STATUS current
            DESCRIPTION
                "Battery constant current test function enable or disable. It is an enumeration value. 
                  If the value is 1, it means the function is disabled; 
                  If the value is 2, it means the function is enabled."
            ::= { hwBattsTest 8 }

        hwSetBattsConsCurrTestDischCurrent OBJECT-TYPE
            SYNTAX Unsigned32 (1..9999)
            MAX-ACCESS read-write
            STATUS current
            DESCRIPTION
                "The battery discharge current in the constant current test. 
                It is an integer value(range:1A~9999A) and the value is accurate to 1A."
            ::= { hwBattsTest 9 }

        hwSetBattsTimeTestMode OBJECT-TYPE
            SYNTAX INTEGER
                {
                disable(1),scheduledTest(3)
                }
            MAX-ACCESS read-write
            STATUS current
            DESCRIPTION
                "Battery constant current test function enable or disable. 
                It is an enumeration value.
                If the value is 1, it means to disable the timed test of battery; 
                If the value is 3, it means to enable the scheduled test of battery."
            ::= { hwBattsTest 10 }

        hwSetBattsScheduledTestPeriod OBJECT-TYPE
            SYNTAX Unsigned32 (2..999)
            MAX-ACCESS read-write
            STATUS current
            DESCRIPTION
                "Scheduled Test Period. 
                Value range: 2 to 999, 
                units: Day, 
                and the value is an integer.(1). 
                If the value is 2147483647(0x7FFFFFFF), it indicates that the value is invalid."
            ::= { hwBattsTest 11 }

        hwSetBattsTestEndCapacity OBJECT-TYPE
            SYNTAX Unsigned32 (0..99)
            MAX-ACCESS read-write
            STATUS current
            DESCRIPTION
                "Test End Capacity.  
                Value range: 0 to 99, 
                units: %, 
                and the value is an integer. 
                If the value is 2147483647(0x7FFFFFFF), it indicates that the value is invalid."
            ::= { hwBattsTest 12 }

        hwSetBattsTestEndTemperature OBJECT-TYPE
            SYNTAX Integer32 (-5..15)
            MAX-ACCESS read-write
            STATUS current
            DESCRIPTION
                "Test End Temperature. 
                Value range: -5 to 15, 
                units: degC, 
                and the value is an integer.(1). 
                If the value is 2147483647(0x7FFFFFFF), it indicates that the value is invalid."
            ::= { hwBattsTest 13 }

        hwSetBattsShortTestEnable OBJECT-TYPE
            SYNTAX INTEGER
                {
                disable(1),enable(2)
                }
            MAX-ACCESS read-write
            STATUS current
            DESCRIPTION
                "Battery short test enable.
                It is an enumeration value, and can be configured. 
                If the enumeration value is 1, it indicates battery short test is disabled;
                If the enumeration value is 2, it indicates battery short test is enabled. "
            ::= { hwBattsTest 14 }

        hwSetBattsShortTestPeriod OBJECT-TYPE
            SYNTAX Unsigned32 (1..360)
            MAX-ACCESS read-write
            STATUS current
            DESCRIPTION
                "Short Test Period. 
                Value range: 1 to 360, 
                units: Day, 
                and the value is an integer.(1). 
                If the value is 2147483647(0x7FFFFFFF), it indicates that the value is invalid."
            ::= { hwBattsTest 15 }

        hwBattString OBJECT IDENTIFIER ::= { hwSiteBatterys 4 }

        hwBattStringConfigTable OBJECT-TYPE
            SYNTAX SEQUENCE OF HwBattStringConfigEntry
            MAX-ACCESS not-accessible
             STATUS current
             DESCRIPTION
                "Battery string config table. Use this table to get battery string equipment ID and equipment name, to set battery standard capacity and battery install time as well. This table's index is hwBattStringConfigIndex, clone battery string config table."
            ::= { hwBattString 1 }

        hwBattStringConfigEntry OBJECT-TYPE
                        SYNTAX HwBattStringConfigEntry
            MAX-ACCESS not-accessible
             STATUS current
             DESCRIPTION
                "Battery string config table. Use this table to get battery string equipment ID and equipment name, to set battery standard capacity and battery install time as well. This table's index is hwBattStringConfigIndex, clone battery string config table."
            INDEX { hwBattStringConfigIndex }
            ::= { hwBattStringConfigTable 1 }

        HwBattStringConfigEntry            ::= SEQUENCE {
                hwBattStringConfigIndex
                    Integer32,
                hwBattStringEquipId
                    Unsigned32,
                hwBattStringEquipName
                    OCTET STRING,
                hwSetBattsTempUpperLimit
                    Integer32,
                hwSetBattsTempLowerLimit
                    Integer32,
                hwSetBattStdCapacity
                    Integer32,
                hwBattStringFatherEquipname
                    OCTET STRING
            }

        hwBattStringConfigIndex OBJECT-TYPE
            SYNTAX Integer32 (1..100)
            MAX-ACCESS read-only
            STATUS current
            DESCRIPTION
                "Device table index of the battery string,
                value range: 1 to 100(To the actual subject)."
            ::= { hwBattStringConfigEntry 1 }

        hwBattStringEquipId OBJECT-TYPE
            SYNTAX Unsigned32 (3001..3100)
            MAX-ACCESS read-only
            STATUS current
            DESCRIPTION
                "Batteries device ID, can be configured by users. 
                Value range: 003,001 to 003,100, in which the first three digits specify the device type and the last three specify the device SN."
            ::= { hwBattStringConfigEntry 2 }

        hwBattStringEquipName OBJECT-TYPE
            SYNTAX OCTET STRING (SIZE (0..63))
            MAX-ACCESS read-only
            STATUS current
            DESCRIPTION
                "Batteries device name, of the character string type, is used to specify the batteries. "
            ::= { hwBattStringConfigEntry 3 }

        hwSetBattsTempUpperLimit OBJECT-TYPE
            SYNTAX Integer32 ( 25..80)
            MAX-ACCESS read-write
            STATUS current
            DESCRIPTION
                "Upper threshold of the battery temperature alarm, can be configured by users. 
                Value range: 25 to 80, 
                Units: centigrade (degC), 
                and the value is an integer (1).  
                If the value is 2147483647(0x7FFFFFFF), it indicates that the value is invalid.
                NOTE: There is linkage between hwSetBattsHTDLimit and hwSetBattsTempUpperLimit"
            ::= { hwBattStringConfigEntry 4 }

        hwSetBattsTempLowerLimit OBJECT-TYPE
            SYNTAX Integer32 ( -20..20)
            MAX-ACCESS read-write
            STATUS current
            DESCRIPTION
                "Lower threshold of the battery temperature alarm, can be configured by users. 
                Value range: -20 to 20, 
                Units: centigrade (degC), 
                and the value is an integer (1).  
                If the value is 2147483647(0x7FFFFFFF), it indicates that the value is invalid."
            ::= { hwBattStringConfigEntry 5 }

        hwSetBattStdCapacity OBJECT-TYPE
            SYNTAX Integer32 (5..12000)
            MAX-ACCESS read-write
            STATUS current
            DESCRIPTION
                "Set battery standard capacity, is an inherent attribute of the device. 
                Value range: 5 to 12000, 
                units: Ah, 
                the value is an integer (1).   
                If the value is 2147483647(0x7FFFFFFF), it indicates that the value is invalid."
            ::= { hwBattStringConfigEntry 8 }

        hwBattStringFatherEquipname OBJECT-TYPE
            SYNTAX OCTET STRING
            MAX-ACCESS read-only
            STATUS current
            DESCRIPTION
                "Name of the parent device of the Batteries"
            ::= { hwBattStringConfigEntry 10 }

        hwBattStringOperTable OBJECT-TYPE
            SYNTAX SEQUENCE OF HwBattStringOperEntry
            MAX-ACCESS not-accessible
             STATUS current
             DESCRIPTION
                "Battery string runing table. 
                Use this table to get battery string current, persent of remain capacity, battery remain capacity, battery actual capacity, as well as  battery temperature. 
                This table's index is hwBattStringRunIndex, clone battery string runing table."
            ::= { hwBattString 2 }

        hwBattStringOperEntry OBJECT-TYPE
                        SYNTAX HwBattStringOperEntry
            MAX-ACCESS not-accessible
             STATUS current
             DESCRIPTION
                "Battery string runing table. 
                Use this table to get battery string current, persent of remain capacity, battery remain capacity, battery actual capacity, as well as  battery temperature. 
                This table's index is hwBattStringRunIndex, clone battery string runing table."
            INDEX { hwBattStringOperIndex }
            ::= { hwBattStringOperTable 1 }

        HwBattStringOperEntry            ::= SEQUENCE {
                hwBattStringOperIndex
                    Integer32,
                hwBattStringCurrent
                    Integer32,
                hwBattStringRemainCapacityPercent
                    Unsigned32,
                hwBattStringRemainCapacity
                    Unsigned32,
                hwBattStringTemprature
                    Integer32,
                hwBattStringMidpointVoltage
                    Integer32,
                hwBattStringOperStatus
                    INTEGER
            }

        hwBattStringOperIndex OBJECT-TYPE
            SYNTAX Integer32 (1..100)
            MAX-ACCESS read-only
            STATUS current
            DESCRIPTION
                "Device table index of the battery string, 
                which value range: 1 to 100(To the actual subject)."
            ::= { hwBattStringOperEntry 1 }

        hwBattStringCurrent OBJECT-TYPE
            SYNTAX Integer32 ( -10000..10000)
            MAX-ACCESS read-only
            STATUS current
            DESCRIPTION
                "Batteries current. It is an analog parameter collected by the battery string in real time. 
                Value range: -1000 to +1000, 
                units: A, 
                and the value is accurate to one decimal place (.1).  
                If the value is 2147483647(0x7FFFFFFF), it indicates that the value is invalid."
            ::= { hwBattStringOperEntry 2 }

        hwBattStringRemainCapacityPercent OBJECT-TYPE
            SYNTAX Unsigned32 (0..1000)
            MAX-ACCESS read-only
            STATUS current
            DESCRIPTION
                "Remaining capacity percentage of the battery string. 
                Value range: 0 to 100, 
                units: %, 
                and the value is accurate to one decimal place (.1).  
                If the value is 2147483647(0x7FFFFFFF), it indicates that the value is invalid."
            ::= { hwBattStringOperEntry 3 }

        hwBattStringRemainCapacity OBJECT-TYPE
            SYNTAX Unsigned32 (5..10000)
            MAX-ACCESS read-only
            STATUS current
            DESCRIPTION
                "Remaining capacity of the battery string. It is an analog parameter collected by the battery string in real time. 
                Value range: 5 to 10000, 
                units: Ah, 
                and the value is an integer (1).  
                If the value is 2147483647(0x7FFFFFFF), it indicates that the value is invalid."
            ::= { hwBattStringOperEntry 4 }

        hwBattStringTemprature OBJECT-TYPE
            SYNTAX Integer32 ( -3000..2000)
            MAX-ACCESS read-only
            STATUS current
            DESCRIPTION
                "Battery temperature. It is a battery parameter collected in real time. 
                Value range: -300 to +200, 
                unit: centigrade (degC), 
                and the value is accurate to one decimal place (.1).
                If the value is 2147483647(0x7FFFFFFF), it indicates that battery temperature sensor is not configured."
            ::= { hwBattStringOperEntry 6 }

        hwBattStringMidpointVoltage OBJECT-TYPE
            SYNTAX Integer32 ( -900..900)
            MAX-ACCESS read-only
            STATUS current
            DESCRIPTION
                "Batteries midpoint voltage. It is an analog parameter collected by the battery string in real time. 
                Value range: -90 to +90, 
                unit: V, 
                and the value is accurate to one decimal place (.1)."
            ::= { hwBattStringOperEntry 7 }

        hwBattStringOperStatus OBJECT-TYPE
            SYNTAX INTEGER
                {
                normal(1),
                tempHigh(2),
                tempLow(3),
                loopBreak(4),
                overCurrent(5),
                unbalance(6),
                discharge(7),
                fuseBreak(8),
                alarmResume(254),
                unknown(255)
                }
            MAX-ACCESS read-only
            STATUS current
            DESCRIPTION
                "State of the site battery string module. It is an enumeration type: 
                  If the enumeration value is 1, it indicates that the site battery string is in the normal state; 
                  If the enumeration value is 2, it indicates that the battery string is over upper alarm threshold of temperature; 
                  If the enumeration value is 3, it indicates that the battery string is under lower alarm threshold of temperature;  
                  If the enumeration value is 4, it indicates that battery string loop has disconnected;  
                  If the enumeration value is 5, it indicates that the current of batery is over upper charging threshold;
                  If the enumeration value is 6, it indicates that the battery string is unbalance;  
                  If the enumeration value is 7, it indicates that battery string is discharge;  
                  If the enumeration value is 8, it indicates that battery string is fuseBreak;
                  If the enumeration value is 254, it indicates battery string alarm resume; 
                  If the enumeration value is 255, it indicates battery string operation status unknown. "
            ::= { hwBattStringOperEntry 99 }

        hwSiteAcDistributions OBJECT IDENTIFIER ::= { hwSiteMonitorMIBObjects 5 }

        hwAcDistributionsGroup OBJECT IDENTIFIER ::= { hwSiteAcDistributions 1 }

        hwAcsGroupId OBJECT-TYPE
            SYNTAX Unsigned32
            MAX-ACCESS read-only
            STATUS current
            DESCRIPTION
                "AC group ID, is the unique ID of the AC group. The first three digits indicate the device type and the last three indicate the device SN. If the last three digits are 000, it indicates a virtual device. "
            ::= { hwAcDistributionsGroup 1 }

        hwAcsGroupName OBJECT-TYPE
            SYNTAX OCTET STRING (SIZE (0..63))
            MAX-ACCESS read-only
            STATUS current
            DESCRIPTION
                "Device name of the AC group. It is of the character string type, and can be configured by users. Otherwise, the configured character can not be any other languages except English."
            ::= { hwAcDistributionsGroup 2 }

        hwAcsTotalCurrent OBJECT-TYPE
            SYNTAX Unsigned32 (0..300000)
            MAX-ACCESS read-only
            STATUS current
            DESCRIPTION
                "Total current of the AC group. It indicates the real-time statistics of the AC group. 
                Value range: 0 to 30000, 
                units: A, 
                and the value is accurate to one decimal place (.1). 
                If the value is 2147483647(0x7FFFFFFF), it indicates that the value is invalid."
            ::= { hwAcDistributionsGroup 3 }

        hwAcsInputQuantity OBJECT-TYPE
            SYNTAX Unsigned32 (0..100)
            MAX-ACCESS read-only
            STATUS current
            DESCRIPTION
                "Total quantity of the site ACUs. Value range: 0 to 100. "
            ::= { hwAcDistributionsGroup 4 }

        hwAcsPowerConsumption OBJECT-TYPE
            SYNTAX Unsigned32 (0..4294967295)
            MAX-ACCESS read-only
            STATUS current
            DESCRIPTION
                "Low 32bits of AC Active power Consumption. Value range:0 to 4294967295, resolution 10wh.
                If GET value is 10, it means  the real consumption is 10*10wh = 100wh (0.1kwh)"
            ::= { hwAcDistributionsGroup 7 }

        hwAcsReactivePowerConsumption OBJECT-TYPE
            SYNTAX Unsigned32 (0..4294967295)
            MAX-ACCESS read-only
            STATUS current
            DESCRIPTION
                "Low 32bits of AC Reactive Power Consumption. Value range:0 to 4294967295, resolution 10varh.
                If GET value is 10, it means  the real consumption is 10*10varh = 100varh (0.1kvarh)"
            ::= { hwAcDistributionsGroup 9 }

        hwAcsReactivePowerConsumptionHigh32b OBJECT-TYPE
            SYNTAX Unsigned32 (0..4294967295)
            MAX-ACCESS read-only
            STATUS current
            DESCRIPTION
                "High 32bits of AC Reactive Power Consumption. Value range:0 to 4294967295, resolution 10varh."
            ::= { hwAcDistributionsGroup 10 }

        hwAcsActivePowerConsumptionKw OBJECT-TYPE
            SYNTAX Unsigned32 (0..4294967295)
            MAX-ACCESS read-only
            STATUS current
            DESCRIPTION
                "AC Active Power Consumption. Value range:0 to 4294967295, resolution 1kwh."
            ::= { hwAcDistributionsGroup 11 }

        hwAcsReactivePowerConsumptionKvar OBJECT-TYPE
            SYNTAX Unsigned32 (0..4294967295)
            MAX-ACCESS read-only
            STATUS current
            DESCRIPTION
                "AC Reactive Power Consumption. Value range:0 to 4294967295, resolution 1kwh."
            ::= { hwAcDistributionsGroup 12 }

        hwAcsPowerConsumptionHigh32b OBJECT-TYPE
            SYNTAX Unsigned32 (0..4294967295)
            MAX-ACCESS read-only
            STATUS current
            DESCRIPTION
                "High 32bits of AC Active Power Consumption. Value range:0 to 4294967295, resolution 10wh."
            ::= { hwAcDistributionsGroup 8 }

        hwAcDistribution OBJECT IDENTIFIER ::= { hwSiteAcDistributions 2 }

        hwAcInputTable OBJECT-TYPE
            SYNTAX SEQUENCE OF HwAcInputEntry
            MAX-ACCESS not-accessible
             STATUS current
             DESCRIPTION
                "AC input table. Use this table to get AC distribution unit ID, AC distribution unit name, A phase or AB line voltage, B phase or BC line voltage, C phase or CA line voltage, AC input breaker status, 
                as well as AC output breakers quantity, which defines hwAcOutputBreakerTable row number. This table's index is hwAcInputIndex, clone AC input table."
            ::= { hwAcDistribution 1 }

        hwAcInputEntry OBJECT-TYPE
                        SYNTAX HwAcInputEntry
            MAX-ACCESS not-accessible
             STATUS current
             DESCRIPTION
                "AC input table. Use this table to get AC distribution unit ID, AC distribution unit name, A phase or AB line voltage, B phase or BC line voltage, C phase or CA line voltage, AC input breaker status, 
                as well as AC output breakers quantity, which defines hwAcOutputBreakerTable row number. This table's index is hwAcInputIndex, clone AC input table."
            INDEX { hwAcInputIndex }
            ::= { hwAcInputTable 1 }

        HwAcInputEntry            ::= SEQUENCE {
                hwAcInputIndex
                    Integer32,
                hwAcEquipId
                    Unsigned32,
                hwAcEquipName
                    OCTET STRING,
                hwApOrAblVoltage
                    Unsigned32,
                hwBpOrBclVoltage
                    Unsigned32,
                hwCpOrCalVoltage
                    Unsigned32,
                hwAphaseCurrent
                    Integer32,
                hwBphaseCurrent
                    Integer32,
                hwCphaseCurrent
                    Integer32,
                hwAcInputBreakersQuantity
                    Unsigned32,
                hwSetAcUpperVoltLimit
                    Unsigned32,
                hwSetAcLowerVoltLimit
                    Unsigned32,
                hwAcFatherEquipname
                    OCTET STRING,
                hwAcInputOperStatus
                    INTEGER
            }

        hwAcInputIndex OBJECT-TYPE
            SYNTAX Integer32 (1..100)
            MAX-ACCESS read-only
            STATUS current
            DESCRIPTION
                "ACU device table index, 
                which value range: 1 to 100. 
                Lines of the device list are restricted by the total quantity of ACUs (hwAcsInputQuantity)."
            ::= { hwAcInputEntry 1 }

        hwAcEquipId OBJECT-TYPE
            SYNTAX Unsigned32
            MAX-ACCESS read-only
            STATUS current
            DESCRIPTION
                "ACU device ID. Value range: 004,001 to 004,100, 
                in which The first digits indicate the device type and the last three digits indicate the device SN."
            ::= { hwAcInputEntry 2 }

        hwAcEquipName OBJECT-TYPE
            SYNTAX OCTET STRING (SIZE (0..63))
            MAX-ACCESS read-only
            STATUS current
            DESCRIPTION
                "ACU device name, of the character string type, is used to specify the alternating current unit (ACU). 
                "
            ::= { hwAcInputEntry 3 }

        hwApOrAblVoltage OBJECT-TYPE
            SYNTAX Unsigned32 (0..8000)
            MAX-ACCESS read-only
            STATUS current
            DESCRIPTION
                "ACU A-phase or AB-line voltage. 
                Value range: 0 to 800, 
                units: V, 
                and the value is accurate to one decimal place (.1).  
                If the value is 2147483647(0x7FFFFFFF), it indicates that the value is invalid."
            ::= { hwAcInputEntry 4 }

        hwBpOrBclVoltage OBJECT-TYPE
            SYNTAX Unsigned32 (0..8000)
            MAX-ACCESS read-only
            STATUS current
            DESCRIPTION
                "ACU B-phase or BC-line voltage. 
                Value range: 0 to 800, 
                units: V, 
                and the value is accurate to one decimal place (.1).  
                If the value is 2147483647(0x7FFFFFFF), it indicates that the value is invalid."
            ::= { hwAcInputEntry 5 }

        hwCpOrCalVoltage OBJECT-TYPE
            SYNTAX Unsigned32 (0..8000)
            MAX-ACCESS read-only
            STATUS current
            DESCRIPTION
                "ACU C-phase or CA-line voltage. 
                Value range: 0 to 800, 
                units: V, 
                and the value is accurate to one decimal place (.1).  
                If the value is 2147483647(0x7FFFFFFF), it indicates that the value is invalid."
            ::= { hwAcInputEntry 6 }

        hwAphaseCurrent OBJECT-TYPE
            SYNTAX Integer32 (0..200000)
            MAX-ACCESS read-only
            STATUS current
            DESCRIPTION
                "ACU A-phase current. It is an analog parameter collected by the ACU in real time. 
                Value range: 0 to 20000, 
                units: A, 
                and the value is accurate to one decimal place (.1).  
                If the value is 2147483647(0x7FFFFFFF), it indicates that the value is invalid."
            ::= { hwAcInputEntry 7 }

        hwBphaseCurrent OBJECT-TYPE
            SYNTAX Integer32 (0..200000)
            MAX-ACCESS read-only
            STATUS current
            DESCRIPTION
                "ACU B-phase current. It is an analog parameter collected by the ACU in real time. 
                Value range: 0 to 20000, 
                units: A, 
                and the value is accurate to one decimal place (.1). 
                If the value is 2147483647(0x7FFFFFFF), it indicates that the value is invalid."
            ::= { hwAcInputEntry 8 }

        hwCphaseCurrent OBJECT-TYPE
            SYNTAX Integer32 (0..200000)
            MAX-ACCESS read-only
            STATUS current
            DESCRIPTION
                "ACU C-phase current. It is an analog parameter collected by the ACU in real time. 
                Value range: 0 to 20000, 
                units: A, 
                and the value is accurate to one decimal place (.1).  
                If the value is 2147483647(0x7FFFFFFF), it indicates that the value is invalid."
            ::= { hwAcInputEntry 9 }

        hwAcInputBreakersQuantity OBJECT-TYPE
            SYNTAX Unsigned32 (0..100)
            MAX-ACCESS read-only
            STATUS current
            DESCRIPTION
                "Quantity of the AC air circuit breakers. 
                As the ACU lower-level subset, the node indicates the quantity of the output air circuit breakers contained by each ACU lower-level subset. Value range: 0 to 100. "
            ::= { hwAcInputEntry 10 }

        hwSetAcUpperVoltLimit OBJECT-TYPE
            SYNTAX Unsigned32 (60..600)
            MAX-ACCESS read-write
            STATUS current
            DESCRIPTION
                "Upper threshold of the AC voltage alarm, can be configured by users. 
                Value range: 60 to 600, 
                units: V, 
                and the value is an integer (1).  
                If the value is 2147483647(0x7FFFFFFF), it indicates that the value is invalid.
                NOTE: There is linkage between hwSetAcsUpperVoltLimit and hwSetAcsLowerVoltLimit.
                If the normal value setting fails, it means that the setting value is not within the support range."
            ::= { hwAcInputEntry 11 }

        hwSetAcLowerVoltLimit OBJECT-TYPE
            SYNTAX Unsigned32 (60..600)
            MAX-ACCESS read-write
            STATUS current
            DESCRIPTION
                "Lower threshold of the AC voltage alarm, can be configured by users. 
                Value range: 60 to 600, 
                units: V, 
                and the value is an integer (1).  
                If the value is 2147483647(0x7FFFFFFF), it indicates that the value is invalid.
                NOTE: There is linkage between hwSetAcsUpperVoltLimit and hwSetAcsLowerVoltLimit.
                If the normal value setting fails, it means that the setting value is not within the support range."
            ::= { hwAcInputEntry 12 }

        hwAcFatherEquipname OBJECT-TYPE
            SYNTAX OCTET STRING
            MAX-ACCESS read-only
            STATUS current
            DESCRIPTION
                "Name of the parent device of the AC"
            ::= { hwAcInputEntry 13 }

        hwAcInputOperStatus OBJECT-TYPE
            SYNTAX INTEGER
                {
                normal(1),
                acOff(2),
                acAbsent(3),
                voltHigh(4),
                voltLow(5),
                freqHigh(6),
                freqLow(7),
                alarmResume(254),
                unknown(255)
                }
            MAX-ACCESS read-only
            STATUS current
            DESCRIPTION
                "State of the site AC distribution uint. It is an enumeration type: 
                  If the enumeration value is 1, it indicates that the site AC distribution uint is in the normal state; 
                  If the enumeration value is 2, it indicates that AC distribution uint power off; 
                  If the enumeration value is 3, it indicates that AC input phase absent;
                  If the enumeration value is 4, it indicates that AC voltage is over upper alarm threshold;  
                  If the enumeration value is 5, it indicates that AC voltage is under lower alarm threshold;  
                  If the enumeration value is 6, it indicates that AC voltage is freqHigh;  
                  If the enumeration value is 7, it indicates that AC voltage is freqLow;  
                  If the enumeration value is 254, it indicates AC distribution uint alarm resume; 
                  If the enumeration value is 255, it indicates AC distribution uint operation status unknown. "
            ::= { hwAcInputEntry 99 }

        hwSiteDcDistributions OBJECT IDENTIFIER ::= { hwSiteMonitorMIBObjects 6 }

        hwDcDistributionsGroup OBJECT IDENTIFIER ::= { hwSiteDcDistributions 1 }

        hwDcsGroupId OBJECT-TYPE
            SYNTAX Unsigned32
            MAX-ACCESS read-only
            STATUS current
            DESCRIPTION
                "DC group ID: unique ID of the DC group. in which The first digits indicate the device type and the last three digits indicate the device SN. If the last three digits are 000, it indicates a virtual device."
            ::= { hwDcDistributionsGroup 1 }

        hwDcsGroupName OBJECT-TYPE
            SYNTAX OCTET STRING (SIZE (0..63))
            MAX-ACCESS read-write
            STATUS current
            DESCRIPTION
                "Device name of the DC group, of the character string type, can be configured by users. Otherwise, the configured character can not be any other languages except English."
            ::= { hwDcDistributionsGroup 2 }

        hwDcsTotalVoltage OBJECT-TYPE
            SYNTAX Unsigned32 (0..1000)
            MAX-ACCESS read-only
            STATUS current
            DESCRIPTION
                "Total voltage of the DC group. 
                Value range: 0 to 100, 
                units: V, 
                and the value is accurate to one decimal place (.1).  
                If the value is 2147483647(0x7FFFFFFF), it indicates that the value is invalid."
            ::= { hwDcDistributionsGroup 3 }

        hwDcsTotalCurrent OBJECT-TYPE
            SYNTAX Integer32 ( -300000..300000)
            MAX-ACCESS read-only
            STATUS current
            DESCRIPTION
                "Total current of the DC group. 
                Value range: -30000 to 30000, 
                units: A, 
                and the value is accurate to one decimal place (.1).   
                If the value is 2147483647(0x7FFFFFFF), it indicates that the value is invalid."
            ::= { hwDcDistributionsGroup 4 }

        hwDcsTotalPower OBJECT-TYPE
            SYNTAX Unsigned32 (0..3000000)
            MAX-ACCESS read-only
            STATUS current
            DESCRIPTION
                "Total power of the DC group. 
                Value range: 0 to 3000000, 
                units: W, 
                and the value is an integer (1).  
                If the value is 2147483647(0x7FFFFFFF), it indicates that the value is invalid."
            ::= { hwDcDistributionsGroup 5 }

        hwDcsTotalQuantity OBJECT-TYPE
            SYNTAX Unsigned32 (0..100)
            MAX-ACCESS read-only
            STATUS current
            DESCRIPTION
                "Total quantity of the DC units, and its Value range: 0 to 100."
            ::= { hwDcDistributionsGroup 6 }

        hwSetDcsUpperVoltLimit OBJECT-TYPE
            SYNTAX Unsigned32 (530..600)
            MAX-ACCESS read-write
            STATUS current
            DESCRIPTION
                "Upper threshold of the DC voltage alarm, can be configued by users. 
                Value range: 53 to 60, 
                units: V, 
                and the value is accurate to one decimal space (.1).  
                If the value is 2147483647(0x7FFFFFFF), it indicates that the value is invalid.
                NOTE: There is linkage between hwSetDcsUpperVoltLimit and hwSetDcsLowerVoltLimit"
            ::= { hwDcDistributionsGroup 7 }

        hwSetDcsLowerVoltLimit OBJECT-TYPE
            SYNTAX Unsigned32 (350..570)
            MAX-ACCESS read-write
            STATUS current
            DESCRIPTION
                "Lower threshold of the DC voltage alarm, can be configued by users. 
                Value range: 35 to 57, 
                units: V, 
                and the value is accurate to one decimal space (.1).  
                If the value is 2147483647(0x7FFFFFFF), it indicates that the value is invalid.
                NOTE: There is linkage between hwSetDcsUpperVoltLimit and hwSetDcsLowerVoltLimit"
            ::= { hwDcDistributionsGroup 8 }

        hwDcsPerfoLoadConsume OBJECT-TYPE
            SYNTAX Unsigned32 (0..429467295)
            MAX-ACCESS read-only
            STATUS current
            DESCRIPTION
                "PerfoLoad Consume of the DC,
                Value range:  0 to 429467295, 
                units: KWh, 
                and the value is an integer (1).
                If the value is 2147483647(0x7FFFFFFF), it indicates that the value is invalid."
            ::= { hwDcDistributionsGroup 9 }

        hwSetDcsUltraUnderVoltThreshold OBJECT-TYPE
            SYNTAX Unsigned32 (360..560)
            MAX-ACCESS read-write
            STATUS current
            DESCRIPTION
                "DC voltage Ultra Low alarm threshold can be configued by users. Value range: 36 to 56, units: V, and the value is accurate to one decimal space (.1).  If the value is 2147483647(0x7FFFFFFF), it indicates that the value is invalid.
                NOTE: There is linkage between hwSetDcsUltraUnderVoltThreshold and hwSetDcsLowerVoltLimit"
            ::= { hwDcDistributionsGroup 11 }

        hwSetDcsUltraOverVoltThreshold OBJECT-TYPE
            SYNTAX Unsigned32 (530..600)
            MAX-ACCESS read-write
            STATUS current
            DESCRIPTION
                "DC voltage Ultra High alarm threshold can be configued by users. Value range: 53 to 60, units: V, and the value is accurate to one decimal space (.1).  If the value is 2147483647(0x7FFFFFFF), it indicates that the value is invalid.
                NOTE: There is linkage between hwSetDcsUpperVoltLimit and hwSetDcsUltraOverVoltThreshold"
            ::= { hwDcDistributionsGroup 10 }

        hwDcDistribution OBJECT IDENTIFIER ::= { hwSiteDcDistributions 2 }

        hwDcOutputTable OBJECT-TYPE
            SYNTAX SEQUENCE OF HwDcOutputEntry
            MAX-ACCESS not-accessible
             STATUS current
             DESCRIPTION
                "/"
            ::= { hwDcDistribution 1 }

        hwDcOutputEntry OBJECT-TYPE
                        SYNTAX HwDcOutputEntry
            MAX-ACCESS not-accessible
             STATUS current
             DESCRIPTION
                "/"
            INDEX { hwDcOutputIndex }
            ::= { hwDcOutputTable 1 }

        HwDcOutputEntry            ::= SEQUENCE {
                hwDcOutputIndex
                    Integer32,
                hwDcOutputEquipId
                    Unsigned32,
                hwDcOutputEquipName
                    OCTET STRING,
                hwDcOutputVoltage
                    Unsigned32,
                hwDcOutputCurrent
                    Integer32,
                hwDcOutputPower
                    Unsigned32,
                hwLoadsQuantity
                    Unsigned32,
                hwLoadUsage
                    Unsigned32,
                hwSetDcUpperVoltLimit
                    Unsigned32,
                hwSetDcLowerVoltLimit
                    Unsigned32,
                hwDcFatherEquipname
                    OCTET STRING,
                hwDcOutputOperStatus
                    INTEGER
            }

        hwDcOutputIndex OBJECT-TYPE
            SYNTAX Integer32 (1..65535)
            MAX-ACCESS read-only
            STATUS current
            DESCRIPTION
                "Device table index of the DC units, which value range: 1 to 65535. Lines of the device list are restricted by the total quantity of DC units (hwDcsQuantity)."
            ::= { hwDcOutputEntry 1 }

        hwDcOutputEquipId OBJECT-TYPE
            SYNTAX Unsigned32 (6001..6100)
            MAX-ACCESS read-only
            STATUS current
            DESCRIPTION
                "DC unit device ID, which value range: 006,001 to 006,100. The first digits indicate the device type and the last three digits indicate the device SN. "
            ::= { hwDcOutputEntry 2 }

        hwDcOutputEquipName OBJECT-TYPE
            SYNTAX OCTET STRING (SIZE (0..63))
            MAX-ACCESS read-only
            STATUS current
            DESCRIPTION
                "DC unit device name, of the character string type."
            ::= { hwDcOutputEntry 3 }

        hwDcOutputVoltage OBJECT-TYPE
            SYNTAX Unsigned32 (0..1000)
            MAX-ACCESS read-only
            STATUS current
            DESCRIPTION
                "DC output voltage. It is an analog parameter collected by the DC power in real time. 
                Value range: 0 to 100, 
                units: V, 
                and the value is accurate to one decimal space (.1).  
                If the value is 2147483647(0x7FFFFFFF), it indicates that the value is invalid."
            ::= { hwDcOutputEntry 4 }

        hwDcOutputCurrent OBJECT-TYPE
            SYNTAX Integer32 ( -300000..300000)
            MAX-ACCESS read-only
            STATUS current
            DESCRIPTION
                "DC output current. It is an analog parameter collected by the DC power in real time. 
                Value range: -30000 to 30000, 
                units: A, 
                and the value is accurate to one decimal space (.1). 
                If the value is 2147483647(0x7FFFFFFF), it indicates that the value is invalid."
            ::= { hwDcOutputEntry 5 }

        hwDcOutputPower OBJECT-TYPE
            SYNTAX Unsigned32 (0..3000000)
            MAX-ACCESS read-only
            STATUS current
            DESCRIPTION
                "DC output power. It is an analog parameter collected by the DC power in real time. 
                Value range: 0 to 10000000, 
                units: W, 
                and the value is an integer (1).  
                If the value is 2147483647(0x7FFFFFFF), it indicates that the value is invalid."
            ::= { hwDcOutputEntry 6 }

        hwLoadsQuantity OBJECT-TYPE
            SYNTAX Unsigned32 (0..100)
            MAX-ACCESS read-only
            STATUS current
            DESCRIPTION
                "Quantity of the DC load output branches, 
                which value range: 0 to 30.  
                As the DC unit lower-level subset, the node indicates the quantity of the DC load output branches contained by each DC unit lower-level subset."
            ::= { hwDcOutputEntry 7 }

        hwLoadUsage OBJECT-TYPE
            SYNTAX Unsigned32 (0..100)
            MAX-ACCESS read-only
            STATUS current
            DESCRIPTION
                "The load usage of rated rectifier capacity. 
                Value range: 0 to 100, 
                units: %, 
                and the value is an integer (1)."
            ::= { hwDcOutputEntry 8 }

        hwSetDcUpperVoltLimit OBJECT-TYPE
            SYNTAX Unsigned32 (530..600)
            MAX-ACCESS read-write
            STATUS current
            DESCRIPTION
                "Upper threshold of the DC voltage alarm, can be configued by users. 
                Value range: 53 to 60, 
                units: V, 
                and the value is accurate to one decimal space (.1).  
                If the value is 2147483647(0x7FFFFFFF), it indicates that the value is invalid.
                NOTE: There is linkage between hwSetDcUpperVoltLimit and hwSetDcLowerVoltLimit"
            ::= { hwDcOutputEntry 10 }

        hwSetDcLowerVoltLimit OBJECT-TYPE
            SYNTAX Unsigned32 (350..570)
            MAX-ACCESS read-write
            STATUS current
            DESCRIPTION
                "Lower threshold of the DC voltage alarm, can be configued by users. 
                Value range: 35 to 57, 
                units: V, 
                and the value is accurate to one decimal space (.1).  
                If the value is 2147483647(0x7FFFFFFF), it indicates that the value is invalid.
                NOTE: There is linkage between hwSetDcUpperVoltLimit and hwSetDcLowerVoltLimit"
            ::= { hwDcOutputEntry 11 }

        hwDcFatherEquipname OBJECT-TYPE
            SYNTAX OCTET STRING
            MAX-ACCESS read-only
            STATUS current
            DESCRIPTION
                "Name of the parent device of the DC"
            ::= { hwDcOutputEntry 9 }

        hwDcOutputOperStatus OBJECT-TYPE
            SYNTAX INTEGER
                {
                normal(1),
                voltHigh(2),
                voltLow(3),
                dcAbsent(4),
                overload(5),
                alarmResume(254),
                unknown(255)
                }
            MAX-ACCESS read-only
            STATUS current
            DESCRIPTION
                "State of the site DC distribution uint. It is an enumeration type: 
                If the enumeration value is 1, it indicates that the site DC distribution uint is in the normal state; 
                If the enumeration value is 2, it indicates that DC voltage is over the upper alarm threshold;
                If the enumeration value is 3, it indicates that DC voltage is under the lower alarm threshold; 
                If the enumeration value is 4, it indicates that DC voltage is dcAbsent; 
                If the enumeration value is 5, it indicates that DC voltage is overload; 
                If the enumeration value is 254, it indicates DC distribution uint alarm resume; 
                If the enumeration value is 255, it indicates DC distribution uint operation status unknown. "
            ::= { hwDcOutputEntry 99 }

        hwLoadBranchTable OBJECT-TYPE
            SYNTAX SEQUENCE OF HwLoadBranchEntry
            MAX-ACCESS not-accessible
             STATUS current
             DESCRIPTION
                "Loads output table. Use this table to get load branch equipment ID, load branch equipment name, load branch current, and load branch power. This table's index is hwLoadBranchIndex, which qualificated by hwloadsQuantity in hwDcOutputTable, clone loads output table."
            ::= { hwDcDistribution 2 }

        hwLoadBranchEntry OBJECT-TYPE
                        SYNTAX HwLoadBranchEntry
            MAX-ACCESS not-accessible
             STATUS current
             DESCRIPTION
                "Loads output table. Use this table to get load branch equipment ID, load branch equipment name, load branch current, and load branch power. This table's index is hwLoadBranchIndex, which qualificated by hwloadsQuantity in hwDcOutputTable, clone loads output table."
            INDEX { hwLoadBranchIndex }
            ::= { hwLoadBranchTable 1 }

        HwLoadBranchEntry            ::= SEQUENCE {
                hwLoadBranchIndex
                    Integer32,
                hwLoadBranchEquipId
                    Unsigned32,
                hwLoadBranchEquipName
                    OCTET STRING,
                hwLoadBranchCurrent
                    Integer32,
                hwLoadBranchPower
                    Unsigned32,
                hwLoadBranchConsume
                    Unsigned32,
                hwLoadBranchConsumption
                    Unsigned32,
                hwLoadBranchConsumptionLow32b
                    Unsigned32,
                hwLoadBranchConsumptionHigh32b
                    Unsigned32,
                hwLoadBranchFatherEquipname
                    OCTET STRING
            }

        hwLoadBranchIndex OBJECT-TYPE
            SYNTAX Integer32 (1..100)
            MAX-ACCESS read-only
            STATUS current
            DESCRIPTION
                "Device table index of the DC load output branch, 
                which value range: 1 to 100.  
                A DC load output branch can be uniquely identified through the DC unit table index and device index of the DC load output branch."
            ::= { hwLoadBranchEntry 1 }

        hwLoadBranchEquipId OBJECT-TYPE
            SYNTAX Unsigned32
            MAX-ACCESS read-only
            STATUS current
            DESCRIPTION
                "Device ID of the DC load output branch. Value range: 007,001 to 007,100. The first digits indicate the device type and the last three digits indicate the SN of the device. "
            ::= { hwLoadBranchEntry 2 }

        hwLoadBranchEquipName OBJECT-TYPE
            SYNTAX OCTET STRING (SIZE (0..63))
            MAX-ACCESS read-only
            STATUS current
            DESCRIPTION
                "Device name of the DC load output branch, of the character string type."
            ::= { hwLoadBranchEntry 3 }

        hwLoadBranchCurrent OBJECT-TYPE
            SYNTAX Integer32 (0..100000)
            MAX-ACCESS read-only
            STATUS current
            DESCRIPTION
                "DC load output branch current. It is an analog parameter collected by the load branch in real time. 
                Value range: 0 to 10000, 
                units: A, 
                and the value is accurate to one decimal space (.1).  
                If the value is 2147483647(0x7FFFFFFF), it indicates that the value is invalid."
            ::= { hwLoadBranchEntry 4 }

        hwLoadBranchPower OBJECT-TYPE
            SYNTAX Unsigned32 (0..600000)
            MAX-ACCESS read-only
            STATUS current
            DESCRIPTION
                "DC load branch power. It is an analog parameter collected by the DC power in real time. 
                Value range: 0 to 3000000, 
                units: W, 
                and the value is an integer (1).  
                If the value is 2147483647(0x7FFFFFFF), it indicates that the value is invalid."
            ::= { hwLoadBranchEntry 5 }

        hwLoadBranchConsume OBJECT-TYPE
            SYNTAX Unsigned32 (0..4294967295)
            MAX-ACCESS read-only
            STATUS current
            DESCRIPTION
                "DC load branch power consumption,
                Value range: 0 to 4294967295, 
                units: KWh, 
                and the value is accurate to one decimal space (.1)."
            ::= { hwLoadBranchEntry 6 }

        hwLoadBranchConsumption OBJECT-TYPE
            SYNTAX Unsigned32 (0..4294967295)
            MAX-ACCESS read-only
            STATUS current
            DESCRIPTION
                "DC load branch power consumption,Value range: 0 to 4294967295, resolution:1 KWh."
            ::= { hwLoadBranchEntry 8 }

        hwLoadBranchConsumptionLow32b OBJECT-TYPE
            SYNTAX Unsigned32 (0..4294967295)
            MAX-ACCESS read-only
            STATUS current
            DESCRIPTION
                "Low 32 bits of DC load branch power consumption,Value range: 0 to 4294967295, resolution:10Wh"
            ::= { hwLoadBranchEntry 9 }

        hwLoadBranchConsumptionHigh32b OBJECT-TYPE
            SYNTAX Unsigned32 (0..4294967295)
            MAX-ACCESS read-only
            STATUS current
            DESCRIPTION
                "High 32 bits of DC load branch power consumption,Value range: 0 to 4294967295, resolution:10Wh"
            ::= { hwLoadBranchEntry 10 }

        hwLoadBranchFatherEquipname OBJECT-TYPE
            SYNTAX OCTET STRING
            MAX-ACCESS read-only
            STATUS current
            DESCRIPTION
                "Name of the parent device of the load output branch."
            ::= { hwLoadBranchEntry 11 }

        hwLvdUnits OBJECT IDENTIFIER ::= { hwSiteMonitorMIBObjects 7 }

        hwLvdsGroup OBJECT IDENTIFIER ::= { hwLvdUnits 1 }

        hwLvdsGroupId OBJECT-TYPE
            SYNTAX Unsigned32
            MAX-ACCESS read-only
            STATUS current
            DESCRIPTION
                "LVD unit group ID. It is the unique ID of the LVD unit group. The first digits indicate the device type. The last three digits indicate the device SN. If the last three digits are 000, it indicates a virtual device."
            ::= { hwLvdsGroup 1 }

        hwLvdsGroupName OBJECT-TYPE
            SYNTAX OCTET STRING (SIZE (0..63))
            MAX-ACCESS read-write
            STATUS current
            DESCRIPTION
                "Low-voltage power-off unit group name, of the character string type, can be configured by users.
                Otherwise, the configured character can not be any other languages except English."
            ::= { hwLvdsGroup 2 }

        hwLvdsTotalQuantity OBJECT-TYPE
            SYNTAX Unsigned32 (0..100)
            MAX-ACCESS read-only
            STATUS current
            DESCRIPTION
                "Total quantity of power-off units. Value range: 0 to 100."
            ::= { hwLvdsGroup 3 }

        hwLvdUnit OBJECT IDENTIFIER ::= { hwLvdUnits 2 }

        hwLvdBranchTable OBJECT-TYPE
            SYNTAX SEQUENCE OF HwLvdBranchEntry
            MAX-ACCESS not-accessible
             STATUS current
             DESCRIPTION
                "Power-off unit table. Use this table to get Lvd unit equipment ID and power-off unit equipment name, set power-off enable and power-off voltage, as well as control power-off unit disconnected. This table's index is hwLvdBranchIndex, which qualificated by hwLvdsQuantity, clone power-off unit table."
            ::= { hwLvdUnit 1 }

        hwLvdBranchEntry OBJECT-TYPE
                        SYNTAX HwLvdBranchEntry
            MAX-ACCESS not-accessible
             STATUS current
             DESCRIPTION
                "Power-off unit table. Use this table to get Lvd unit equipment ID and power-off unit equipment name, set power-off enable and power-off voltage, as well as control power-off unit disconnected. This table's index is hwLvdBranchIndex, which qualificated by hwLvdsQuantity, clone power-off unit table."
            INDEX { hwLvdBranchIndex }
            ::= { hwLvdBranchTable 1 }

        HwLvdBranchEntry            ::= SEQUENCE {
                hwLvdBranchIndex
                    Integer32,
                hwLvdUnitEquipId
                    Unsigned32,
                hwLvdUnitEquipName
                    OCTET STRING,
                hwSetLvdEnable
                    INTEGER,
                hwSetLvdVoltage
                    Integer32,
                hwCtrlLvd
                    INTEGER,
                hwSetLvdMode
                    INTEGER,
                hwSetLvdReconnectedVoltage
                    Integer32,
                hwSetLvdDisconnectedTime
                    Integer32,
                hwSetLvdDisconnectedCapacity
                    Integer32,
                hwLvdBranchOperStatus
                    INTEGER,
                hwLvdBranchRowStatus
                    RowStatus
            }

        hwLvdBranchIndex OBJECT-TYPE
            SYNTAX Integer32 (1..100)
            MAX-ACCESS read-only
            STATUS current
            DESCRIPTION
                "Device table index of a power-off unit. 
                Value range: 1 to 100. Lines of the device list are restricted by the total quantity of the power-off units (hwLvdsTotalQuantity). "
            ::= { hwLvdBranchEntry 1 }

        hwLvdUnitEquipId OBJECT-TYPE
            SYNTAX Unsigned32 (8001..8100)
            MAX-ACCESS read-only
            STATUS current
            DESCRIPTION
                "Device ID of a power-off unit."
            ::= { hwLvdBranchEntry 2 }

        hwLvdUnitEquipName OBJECT-TYPE
            SYNTAX OCTET STRING (SIZE (0..63))
            MAX-ACCESS read-only
            STATUS current
            DESCRIPTION
                "Device name of a power-off unit, of the character string type, is used to specify the low-voltage power-off unit. Users can configure it. Otherwise, the configured character can not be any other languages except English. "
            ::= { hwLvdBranchEntry 3 }

        hwSetLvdEnable OBJECT-TYPE
            SYNTAX INTEGER
                {
                enabled(1),
                disabled(2)
                }
            MAX-ACCESS read-write
            STATUS current
            DESCRIPTION
                "Control power-off unit enabling. It is an enumeration value, and users actively set it. 
                  If the enumeration value is 1, it means to enable the power-off unit; 
                  If the enumeration value is 2, it means to disable the power-off unit. 
                  When the power-off unit control is not configured, the power-off unit is enabled by default."
            ::= { hwLvdBranchEntry 4 }

        hwSetLvdVoltage OBJECT-TYPE
            SYNTAX Integer32 (350..560)
            MAX-ACCESS read-write
            STATUS current
            DESCRIPTION
                "Low-voltage power-off voltage of a power-off unit can be configured by users. 
                Its value range: 35 to 56, 
                units: V, 
                and the value is accurate to one decimal space (.1).  
                If the value is 2147483647(0x7FFFFFFF), it indicates that the value is invalid.
                NOTE: There is linkage between hwSetLvdVoltage and hwSetLvdReconnectedVoltage"
            ::= { hwLvdBranchEntry 5 }

        hwCtrlLvd OBJECT-TYPE
            SYNTAX INTEGER
                {
                powerOff(1),
                powerOn(2),
                nullOper(255)
                }
            MAX-ACCESS read-write
            STATUS current
            DESCRIPTION
                "Control of the power-off unit. It is an enumeration value, users control it manually. 
                  If the NMS notifies the SNMP agent that the node is set to 1, it means to power off the power-off unit; 
                  If the NMS notifies the SNMP agent that the node is set to 2, it means that the background controls the power-on of the LVD unit. 
                  If the NMS notifies the SNMP agent that the node is set to 255, it means that the background controls the nulloper of the LVD unit.
                NOTE: Only the system in manual mode, this parameter can be configured successfully.
                "
            ::= { hwLvdBranchEntry 6 }

        hwSetLvdMode OBJECT-TYPE
            SYNTAX INTEGER
                {
                byVoltage(1),
                byTime(2),
                byCapacity(3),
                unknown(255)
                }
            MAX-ACCESS read-write
            STATUS current
            DESCRIPTION
                "Select the control mode of the power-off unit. It is an enumeration value, users can configure it manually. 
                    If the NMS notifies the SNMP agent that the node is set to 1, it means to select the voltage power off mode; 
                    If the NMS notifies the SNMP agent that the node is set to 2, it means to select the time power off mode;  
                    If the NMS notifies the SNMP agent that the node is set to 3, it means to select the capacity power off mode;
                    If the NMS notifies the SNMP agent that the node is set to 255, it means to select the capacity power unknown mode;"
            ::= { hwLvdBranchEntry 7 }

        hwSetLvdReconnectedVoltage OBJECT-TYPE
            SYNTAX Integer32 (370..580)
            MAX-ACCESS read-write
            STATUS current
            DESCRIPTION
                "Low-voltage power-off recover of a power-off unit can be configured by users. 
                Its value range: 37.0 to 58.0, 
                unit: V, 
                and the value is accurate to one decimal space (.1).  
                If the value is 2147483647(0x7FFFFFFF), it indicates that the value is invalid.
                The default value is 51.5
                NOTE: There is linkage between hwSetLvdVoltage and hwSetLvdReconnectedVoltage"
            ::= { hwLvdBranchEntry 8 }

        hwSetLvdDisconnectedTime OBJECT-TYPE
            SYNTAX Integer32 (5..1000)
            MAX-ACCESS read-write
            STATUS current
            DESCRIPTION
                "Low-voltage power-off disconnected time, It can be configured by users,
                value range defines between 5 to 1000, 
                unit: minutes(min) ，
                and its value is an integer (1). 
                Here, if battery manual test is standard mode, 
                If the value is 2147483647(0x7FFFFFFF), it indicates that the value is invalid.
                NOTE: Only the lvd in time power off mode, this parameter can be configured successfully."
            ::= { hwLvdBranchEntry 9 }

        hwSetLvdDisconnectedCapacity OBJECT-TYPE
            SYNTAX Integer32 (0..1000)
            MAX-ACCESS read-write
            STATUS current
            DESCRIPTION
                "Power-off unit control the power off, when Remaining capacity percentage of the battery strings is below the calue. 
                Value range: 0 to 100, 
                unit: %, 
                and the value is accurate to one decimal space (.1). 
                If the value is 2147483647(0x7FFFFFFF), it indicates that the value is invalid.
                NOTE: Only the lvd in capacity power off mode, this parameter can be configured successfully."
            ::= { hwLvdBranchEntry 10 }

        hwLvdBranchOperStatus OBJECT-TYPE
            SYNTAX INTEGER
                {
                normal(1),
                lowVoltOff(2),
                backgroundOff(3),
                localManualOff(4),
                lowTempOff(5),
                highTempOff(6),
                timeOff(7),
                capacityOff(8),
                forceOff(9),
                maintenanceOff(10),
                alarmResume(254),
                unknown(255)
                }
            MAX-ACCESS read-only
            STATUS current
            DESCRIPTION
                "State of the site LVD uint. It is an enumeration type: 
                  If the enumeration value is 1, the site LVD uint is in the normal state;
                  If the enumeration value is 2, the power-off uint disconnect for low voltage;  
                  If the enumeration value is 3, the power-off uint disconnect bakeground;   
                  If the enumeration value is 4, the power-off uint local disconnect manually;  
                  If the enumeration value is 5, the power-off uint disconnect for under temperature; 
                  If the enumeration value is 6, the power-off uint disconnect for over temperature; 
                  If the enumeration value is 7, the ower-off uint disconnect for time;
                If the enumeration value is 8, the power-off uint disconnect for capacity;
                If the enumeration value is 9, the power-off uint disconnect for force;
                If the enumeration value is 10, the power-off uint disconnect for maintenance;
                  If the enumeration value is 254, the power-off uint alarm resume; 
                  If the enumeration value is 255, it indicates LVD uint operation status unknown. "
            ::= { hwLvdBranchEntry 99 }

        hwLvdBranchRowStatus OBJECT-TYPE
            SYNTAX RowStatus
            MAX-ACCESS read-create
            STATUS current
            DESCRIPTION
                "RowStatus of lvd table."
            ::= { hwLvdBranchEntry 100 }

        hwDcLvdTable OBJECT-TYPE
            SYNTAX SEQUENCE OF HwDcLvdEntry
            MAX-ACCESS not-accessible
             STATUS current
             DESCRIPTION
                "Power-off unit table. Use this table to get Lvd unit equipment ID and power-off unit equipment name, set power-off enable and power-off voltage, as well as control power-off unit disconnected. This table's index is hwLvdBranchIndex, which qualificated by hwLvdsQuantity, clone power-off unit table."
            ::= { hwLvdUnit 2 }

        hwDcLvdEntry OBJECT-TYPE
                        SYNTAX HwDcLvdEntry
            MAX-ACCESS not-accessible
             STATUS current
             DESCRIPTION
                "Power-off unit table. Use this table to get Lvd unit equipment ID and power-off unit equipment name, set power-off enable and power-off voltage, as well as control power-off unit disconnected. This table's index is hwLvdBranchIndex, which qualificated by hwLvdsQuantity, clone power-off unit table."
            INDEX { hwDcLvdIndex }
            ::= { hwDcLvdTable 1 }

        HwDcLvdEntry            ::= SEQUENCE {
                hwDcLvdIndex
                    Integer32,
                hwDcLvdEquipId
                    Unsigned32,
                hwDcLvdEquipName
                    OCTET STRING,
                hwDcSetLvdEnable
                    INTEGER,
                hwDcSetLvdVoltage
                    Integer32,
                hwDcCtrlLvd
                    INTEGER,
                hwDcSetLvdMode
                    INTEGER,
                hwDcSetLvdReconnectedVoltage
                    Integer32,
                hwDcSetLvdDisconnectedTime
                    Integer32,
                hwDcSetLvdDisconnectedCapacity
                    Integer32,
                hwDcLvdFatherEquipname
                    OCTET STRING
            }

        hwDcLvdIndex OBJECT-TYPE
            SYNTAX Integer32 (1..100)
            MAX-ACCESS read-only
            STATUS current
            DESCRIPTION
                "Device table index of a power-off unit. 
                Value range: 1 to 100. Lines of the device list are restricted by the total quantity of the power-off units (hwLvdsTotalQuantity). "
            ::= { hwDcLvdEntry 1 }

        hwDcLvdEquipId OBJECT-TYPE
            SYNTAX Unsigned32
            MAX-ACCESS read-only
            STATUS current
            DESCRIPTION
                "Device ID of a power-off unit."
            ::= { hwDcLvdEntry 2 }

        hwDcLvdEquipName OBJECT-TYPE
            SYNTAX OCTET STRING (SIZE (0..63))
            MAX-ACCESS read-only
            STATUS current
            DESCRIPTION
                "Device name of a power-off unit, of the character string type, is used to specify the low-voltage power-off unit. Users can configure it. Otherwise, the configured character can not be any other languages except English. "
            ::= { hwDcLvdEntry 3 }

        hwDcSetLvdEnable OBJECT-TYPE
            SYNTAX INTEGER
                {
                enabled(1),
                disabled(2)
                }
            MAX-ACCESS read-write
            STATUS current
            DESCRIPTION
                "Control power-off unit enabling. It is an enumeration value, and users actively set it. 
                If the enumeration value is 1, it means to enable the power-off unit; 
                If the enumeration value is 2, it means to disable the power-off unit. 
                When the power-off unit control is not configured, the power-off unit is enabled by default.
                Instance number:
                1---LLVD1
                2---LLVD2
                3---BLVD
                4---LLVD3
                5---LLVD4"
            ::= { hwDcLvdEntry 4 }

        hwDcSetLvdVoltage OBJECT-TYPE
            SYNTAX Integer32 (350..560)
            MAX-ACCESS read-write
            STATUS current
            DESCRIPTION
                "Low-voltage power-off voltage of a power-off unit can be configured by users. Its value range: 35 to 56, units: V, and the value is accurate to one decimal space (.1).  If the value is 2147483647(0x7FFFFFFF), it indicates that the value is invalid.
                NOTE: There is linkage between hwSetLvdVoltage and hwSetLvdReconnectedVoltage
                Instance number:
                1---LLVD1
                2---LLVD2
                3---BLVD
                4---LLVD3
                5---LLVD4"
            ::= { hwDcLvdEntry 5 }

        hwDcCtrlLvd OBJECT-TYPE
            SYNTAX INTEGER
                {
                powerOff(1),
                powerOn(2),
                nullOper(255)
                }
            MAX-ACCESS read-write
            STATUS current
            DESCRIPTION
                "Control of the power-off unit. It is an enumeration value, users control it manually. 
                  If the NMS notifies the SNMP agent that the node is set to 1, it means to power off the power-off unit; 
                  If the NMS notifies the SNMP agent that the node is set to 2, it means that the background controls the power-on of the LVD unit. 
                  If the NMS notifies the SNMP agent that the node is set to 255, it means that the background controls the nulloper of the LVD unit.
                NOTE: Only the system in manual mode, this parameter can be configured successfully.
                "
            ::= { hwDcLvdEntry 6 }

        hwDcSetLvdMode OBJECT-TYPE
            SYNTAX INTEGER
                {
                byVoltage(1),
                byTime(2),
                byCapacity(3),
                unknown(255)
                }
            MAX-ACCESS read-write
            STATUS current
            DESCRIPTION
                "Select the control mode of the power-off unit. It is an enumeration value, users can configure it manually. 
                    If the NMS notifies the SNMP agent that the node is set to 1, it means to select the voltage power off mode; 
                    If the NMS notifies the SNMP agent that the node is set to 2, it means to select the time power off mode;  
                    If the NMS notifies the SNMP agent that the node is set to 3, it means to select the capacity power off mode;
                    If the NMS notifies the SNMP agent that the node is set to 255, it means to select the capacity power unknown mode;"
            ::= { hwDcLvdEntry 7 }

        hwDcSetLvdReconnectedVoltage OBJECT-TYPE
            SYNTAX Integer32 (370..580)
            MAX-ACCESS read-write
            STATUS current
            DESCRIPTION
                "Low-voltage power-off recover of a power-off unit can be configured by users. 
                Its value range: 37.0 to 58.0, 
                unit: V, 
                and the value is accurate to one decimal space (.1).  
                If the value is 2147483647(0x7FFFFFFF), it indicates that the value is invalid.
                The default value is 51.5
                NOTE: There is linkage between hwSetLvdVoltage and hwSetLvdReconnectedVoltage"
            ::= { hwDcLvdEntry 8 }

        hwDcSetLvdDisconnectedTime OBJECT-TYPE
            SYNTAX Integer32 (5..1000)
            MAX-ACCESS read-write
            STATUS current
            DESCRIPTION
                "Low-voltage power-off disconnected time, It can be configured by users,
                value range defines between 5 to 1000, 
                unit: minutes(min) ，
                and its value is an integer (1). 
                Here, if battery manual test is standard mode, 
                If the value is 2147483647(0x7FFFFFFF), it indicates that the value is invalid.
                NOTE: Only the lvd in time power off mode, this parameter can be configured successfully."
            ::= { hwDcLvdEntry 9 }

        hwDcSetLvdDisconnectedCapacity OBJECT-TYPE
            SYNTAX Integer32 (0..1000)
            MAX-ACCESS read-write
            STATUS current
            DESCRIPTION
                "Power-off unit control the power off, when Remaining capacity percentage of the battery strings is below the calue. 
                Value range: 0 to 100, 
                unit: %, 
                and the value is accurate to one decimal space (.1). 
                If the value is 2147483647(0x7FFFFFFF), it indicates that the value is invalid.
                NOTE: Only the lvd in capacity power off mode, this parameter can be configured successfully."
            ::= { hwDcLvdEntry 10 }

        hwDcLvdFatherEquipname OBJECT-TYPE
            SYNTAX OCTET STRING
            MAX-ACCESS read-only
            STATUS current
            DESCRIPTION
                "Name of the parent device of the power-off unit"
            ::= { hwDcLvdEntry 11 }

        hwBlvdTable OBJECT-TYPE
            SYNTAX SEQUENCE OF HwBlvdEntry
            MAX-ACCESS not-accessible
             STATUS current
             DESCRIPTION
                "Power-off unit table."
            ::= { hwLvdUnit 3 }

        hwBlvdEntry OBJECT-TYPE
                        SYNTAX HwBlvdEntry
            MAX-ACCESS not-accessible
             STATUS current
             DESCRIPTION
                "Power-off unit table."
            INDEX { hwBlvdIndex }
            ::= { hwBlvdTable 1 }

        HwBlvdEntry            ::= SEQUENCE {
                hwBlvdIndex
                    Integer32,
                hwBlvdEquipId
                    Unsigned32,
                hwBlvdEquipName
                    OCTET STRING,
                hwSetBlvdEnable
                    INTEGER,
                hwSetBlvdVoltage
                    Integer32,
                hwCtrlBlvd
                    INTEGER,
                hwSetBlvdMode
                    INTEGER,
                hwSetBlvdReconnectedVoltage
                    Integer32,
                hwSetBlvdDisconnectedTime
                    Integer32,
                hwSetBlvdDisconnectedCapacity
                    Integer32,
                hwBlvdFatherEquipname
                    OCTET STRING
            }

        hwBlvdIndex OBJECT-TYPE
            SYNTAX Integer32 (1..100)
            MAX-ACCESS read-only
            STATUS current
            DESCRIPTION
                "Device table index of a power-off unit. "
            ::= { hwBlvdEntry 1 }

        hwBlvdEquipId OBJECT-TYPE
            SYNTAX Unsigned32
            MAX-ACCESS read-only
            STATUS current
            DESCRIPTION
                "Device ID of a power-off unit."
            ::= { hwBlvdEntry 2 }

        hwBlvdEquipName OBJECT-TYPE
            SYNTAX OCTET STRING (SIZE (0..63))
            MAX-ACCESS read-only
            STATUS current
            DESCRIPTION
                "Device name of a power-off unit"
            ::= { hwBlvdEntry 3 }

        hwSetBlvdEnable OBJECT-TYPE
            SYNTAX INTEGER
                {
                enabled(1),
                disabled(2)
                }
            MAX-ACCESS read-write
            STATUS current
            DESCRIPTION
                "Control power-off unit enabling. It is an enumeration value, and users actively set it. 
                  If the enumeration value is 1, it means to enable the power-off unit; 
                  If the enumeration value is 2, it means to disable the power-off unit. 
                  When the power-off unit control is not configured, the power-off unit is enabled by default."
            ::= { hwBlvdEntry 4 }

        hwSetBlvdVoltage OBJECT-TYPE
            SYNTAX Integer32 (360..560)
            MAX-ACCESS read-write
            STATUS current
            DESCRIPTION
                "Low-voltage power-off voltage of a power-off unit can be configured by users. 
                Its value range: 36 to 56, 
                units: V, 
                and the value is accurate to one decimal space (.1).  
                If the value is 2147483647(0x7FFFFFFF), it indicates that the value is invalid.
                NOTE: There is linkage between hwSetBlvdVoltage and hwSetBlvdReconnectedVoltage"
            ::= { hwBlvdEntry 5 }

        hwCtrlBlvd OBJECT-TYPE
            SYNTAX INTEGER
                {
                powerOff(1),
                powerOn(2),
                nullOper(255)
                }
            MAX-ACCESS read-write
            STATUS current
            DESCRIPTION
                "Control of the power-off unit. It is an enumeration value, users control it manually. 
                  If the NMS notifies the SNMP agent that the node is set to 1, it means to power off the power-off unit; 
                  If the NMS notifies the SNMP agent that the node is set to 2, it means that the background controls the power-on of the Blvd unit. 
                  If the NMS notifies the SNMP agent that the node is set to 255, it means that the background controls the nulloper of the Blvd unit.
                NOTE: Only the system in manual mode, this parameter can be configured successfully.
                "
            ::= { hwBlvdEntry 6 }

        hwSetBlvdMode OBJECT-TYPE
            SYNTAX INTEGER
                {
                byVoltage(1),
                byTime(2),
                byCapacity(3),
                unknown(255)
                }
            MAX-ACCESS read-write
            STATUS current
            DESCRIPTION
                "Select the control mode of the power-off unit. It is an enumeration value, users can configure it manually. 
                    If the NMS notifies the SNMP agent that the node is set to 1, it means to select the voltage power off mode; 
                    If the NMS notifies the SNMP agent that the node is set to 2, it means to select the time power off mode;  
                    If the NMS notifies the SNMP agent that the node is set to 3, it means to select the capacity power off mode;
                    If the NMS notifies the SNMP agent that the node is set to 255, it means to select the capacity power unknown mode;"
            ::= { hwBlvdEntry 7 }

        hwSetBlvdReconnectedVoltage OBJECT-TYPE
            SYNTAX Integer32 (370..580)
            MAX-ACCESS read-write
            STATUS current
            DESCRIPTION
                "Low-voltage power-off recover of a power-off unit can be configured by users. 
                Its value range: 37.0 to 58.0, 
                unit: V, 
                and the value is accurate to one decimal space (.1).  
                If the value is 2147483647(0x7FFFFFFF), it indicates that the value is invalid.
                NOTE: There is linkage between hwSetBlvdVoltage and hwSetBlvdReconnectedVoltage"
            ::= { hwBlvdEntry 8 }

        hwSetBlvdDisconnectedTime OBJECT-TYPE
            SYNTAX Integer32 (5..1000)
            MAX-ACCESS read-write
            STATUS current
            DESCRIPTION
                "Low-voltage power-off disconnected time, It can be configured by users,
                value range defines between 5 to 1000, 
                unit: minutes(min) ，
                and its value is an integer (1). 
                Here, if battery manual test is standard mode, 
                If the value is 2147483647(0x7FFFFFFF), it indicates that the value is invalid.
                NOTE: Only the Blvd in time power off mode, this parameter can be configured successfully."
            ::= { hwBlvdEntry 9 }

        hwSetBlvdDisconnectedCapacity OBJECT-TYPE
            SYNTAX Integer32 (0..1000)
            MAX-ACCESS read-write
            STATUS current
            DESCRIPTION
                "Power-off unit control the power off, when Remaining capacity percentage of the battery strings is below the calue. 
                Value range: 0 to 100, 
                unit: %, 
                and the value is accurate to one decimal space (.1). 
                If the value is 2147483647(0x7FFFFFFF), it indicates that the value is invalid.
                NOTE: Only the Blvd in capacity power off mode, this parameter can be configured successfully."
            ::= { hwBlvdEntry 10 }

        hwBlvdFatherEquipname OBJECT-TYPE
            SYNTAX OCTET STRING
            MAX-ACCESS read-only
            STATUS current
            DESCRIPTION
                "Name of the parent device of the power-off unit"
            ::= { hwBlvdEntry 11 }

        hwSiteEnvUnits OBJECT IDENTIFIER ::= { hwSiteMonitorMIBObjects 8 }

        hwEnvUnitsGroup OBJECT IDENTIFIER ::= { hwSiteEnvUnits 1 }

        hwEnvUnitsGroupId OBJECT-TYPE
            SYNTAX Unsigned32
            MAX-ACCESS read-only
            STATUS current
            DESCRIPTION
                "Unit group ID of the site environment. It is the unique ID of the unit group on the site. 
                The first digits indicate the device type. The last three digits indicate the device SN. If the last three digits are 000, it indicates a virtual device. "
            ::= { hwEnvUnitsGroup 1 }

        hwEnvUnitsGroupName OBJECT-TYPE
            SYNTAX OCTET STRING (SIZE (0..63))
            MAX-ACCESS read-write
            STATUS current
            DESCRIPTION
                "Unit group name of the site environment, of the character string type, can be configured by users.
                Otherwise, the configured character can not be any other languages except English."
            ::= { hwEnvUnitsGroup 2 }

        hwCtrlSmokeReset OBJECT-TYPE
            SYNTAX INTEGER
                {
                normal(1),
                reset(2),
                nullOper(255)
                }
            MAX-ACCESS read-write
            STATUS current
            DESCRIPTION
                "Smoke sensor reset. It manually controls clearance of the smoke sensor alarm, and this node is of the enumeration type. 
                If the enumeration value of the node is 1, it indicates that the reset of the smoke sensor is not required. 
                If the enumeration value of the node is 2, it indicates that the background controls the reset of the smoke sensor. 
                If the enumeration value of the node is 255, it indicates that the background controls the unknown of the smoke sensor. "
            ::= { hwEnvUnitsGroup 3 }

        hwCtrlBuzzerEnable OBJECT-TYPE
            SYNTAX INTEGER
                {
                enable(1),
                disable(2),
                nullOper(255)
                }
            MAX-ACCESS read-write
            STATUS current
            DESCRIPTION
                "Buzzer enabling. It manually controls the enabling of the buzzer alarm. This node is of the enumeration type. 
                When the enumeration value is 1, it means to enable the buzzer;
                When the enumeration value is 2, it means to disable the buzzer. 
                When the enumeration value is 255, it means to nulloper the buzzer. 
                "
            ::= { hwEnvUnitsGroup 5 }

        hwEnvTempSensorsTotalQuantity OBJECT-TYPE
            SYNTAX Unsigned32 (0..256)
            MAX-ACCESS read-only
            STATUS current
            DESCRIPTION
                "Quantity of the environment temperature sensors, and its value range: 0 to 256."
            ::= { hwEnvUnitsGroup 6 }

        hwEnvHumiSensorsTotalQuantity OBJECT-TYPE
            SYNTAX Unsigned32 (0..256)
            MAX-ACCESS read-only
            STATUS current
            DESCRIPTION
                "Quantity of the environment humidity sensors, and its value range: 0 to 256."
            ::= { hwEnvUnitsGroup 7 }

        hwSpareDigitalsTotalQuantity OBJECT-TYPE
            SYNTAX Unsigned32 (0..256)
            MAX-ACCESS read-only
            STATUS current
            DESCRIPTION
                "Quantity of the Spare digitals, and its value range: 0 to 256."
            ::= { hwEnvUnitsGroup 8 }

        hwSpareDigitalsOutputQuantity OBJECT-TYPE
            SYNTAX Unsigned32 (0..256)
            MAX-ACCESS read-only
            STATUS current
            DESCRIPTION
                "Quantity of the Spare digitals Output, and its value range: 0 to 256."
            ::= { hwEnvUnitsGroup 9 }

        hwEnvSensor OBJECT IDENTIFIER ::= { hwSiteEnvUnits 2 }

        hwEnvTempSensorTable OBJECT-TYPE
            SYNTAX SEQUENCE OF HwEnvTempSensorEntry
            MAX-ACCESS not-accessible
             STATUS current
             DESCRIPTION
                "Site environment temperature table. 
                Use this table to get environment temperature equipment ID, environment temperature equipment name, and environment temperature, set environment temperature upper limit, environment temperature lower limit, and environment temperature alarm enable. 
                This table's index is hwEnvTempSensorIndex, which qualificated by hwEnvTempSensorsQuantity, clone site environment temperature table."
            ::= { hwEnvSensor 1 }

        hwEnvTempSensorEntry OBJECT-TYPE
                        SYNTAX HwEnvTempSensorEntry
            MAX-ACCESS not-accessible
             STATUS current
             DESCRIPTION
                "Site environment temperature table. 
                Use this table to get environment temperature equipment ID, environment temperature equipment name, and environment temperature, set environment temperature upper limit, environment temperature lower limit, and environment temperature alarm enable. 
                This table's index is hwEnvTempSensorIndex, which qualificated by hwEnvTempSensorsQuantity, clone site environment temperature table."
            INDEX { hwEnvTempSensorIndex }
            ::= { hwEnvTempSensorTable 1 }

        HwEnvTempSensorEntry            ::= SEQUENCE {
                hwEnvTempSensorIndex
                    Integer32,
                hwEnvTempEquipId
                    Unsigned32,
                hwEnvTempEquipName
                    OCTET STRING,
                hwEnvTemperature
                    Integer32,
                hwSetEnvTempUpperLimit
                    Integer32,
                hwSetEnvTempLowerLimit
                    Integer32,
                hwSetEnvTempUltraHighTempThreshold
                    Unsigned32,
                hwEnvTempSensorOperStatus
                    INTEGER,
                hwEnvTempFatherEquipname
                    OCTET STRING,
                hwEnvTempSensorRowStatus
                    RowStatus
            }

        hwEnvTempSensorIndex OBJECT-TYPE
            SYNTAX Integer32
            MAX-ACCESS read-only
            STATUS current
            DESCRIPTION
                "Table index of the environment temperature sensors."
            ::= { hwEnvTempSensorEntry 1 }

        hwEnvTempEquipId OBJECT-TYPE
            SYNTAX Unsigned32 (9001..9255)
            MAX-ACCESS read-only
            STATUS current
            DESCRIPTION
                "Environment temperature sensor ID. Value range: 009'001 to 009'255, in which the first digits indicate the device type and the last three digits indicate the device SN. "
            ::= { hwEnvTempSensorEntry 2 }

        hwEnvTempEquipName OBJECT-TYPE
            SYNTAX OCTET STRING (SIZE (0..63))
            MAX-ACCESS read-only
            STATUS current
            DESCRIPTION
                "Environment temperature sensor name, of the character string type,  is used to specify an environment temperature sensor. "
            ::= { hwEnvTempSensorEntry 3 }

        hwEnvTemperature OBJECT-TYPE
            SYNTAX Integer32 ( -50..100)
            MAX-ACCESS read-only
            STATUS current
            DESCRIPTION
                "Environment temperature. It is an environment parameter collected in real time. 
                Value range: -50 to +100, 
                units: centigrade (degC), 
                and the value is an integer (1).  
                If the value is 2147483647, it indicates that the temperature sensor is not configured."
            ::= { hwEnvTempSensorEntry 4 }

        hwSetEnvTempUpperLimit OBJECT-TYPE
            SYNTAX Integer32 ( 25..80)
            MAX-ACCESS read-write
            STATUS current
            DESCRIPTION
                "Upper threshold of the environment temperature alarm, can be configured by users. Value range: 25 to 80, units: centigrade (degC), and the value is an integer (1).  If the value is 2147483647(0x7FFFFFFF), it indicates that the value is invalid."
            ::= { hwEnvTempSensorEntry 5 }

        hwSetEnvTempLowerLimit OBJECT-TYPE
            SYNTAX Integer32 ( -20..20)
            MAX-ACCESS read-write
            STATUS current
            DESCRIPTION
                "Lower threshold of the environment temperature alarm, can be configured by users. Value range: -20 to 20, units: centigrade (degC), and the value is an integer (1).  If the value is 2147483647(0x7FFFFFFF), it indicates that the value is invalid."
            ::= { hwEnvTempSensorEntry 6 }

        hwSetEnvTempUltraHighTempThreshold OBJECT-TYPE
            SYNTAX Unsigned32 (25..80)
            MAX-ACCESS read-write
            STATUS current
            DESCRIPTION
                "Threshold of the environment ultra high temperature measurement, can be configured by users.
                Value range: 25 to 80,
                unit: centigrade (degC),
                and the value is an integer (1).
                If the value is 2147483647(0x7FFFFFFF), it indicates that the value is invalid.
                "
            ::= { hwEnvTempSensorEntry 10 }

        hwEnvTempSensorOperStatus OBJECT-TYPE
            SYNTAX INTEGER
                {
                normal(1),
                tempHigh(2),
                tempLow(3),
                notInslot(4),
                alarmResume(254),
                unknown(255)
                }
            MAX-ACCESS read-only
            STATUS current
            DESCRIPTION
                "State of the site environment temperature sensor. It is an enumeration type: 
                  If the enumeration value is 1, it indicates that the site environment temperature sensor is in the normal state; 
                  If the enumeration value is 2, it indicates that the environment temperature sensor is over temperature; 
                  If the enumeration value is 3, it indicates that the environment temperature sensor is under temperature; 
                  If the enumeration value is 4, it indicates that the environment temperature sensor is not in slot;
                  If the enumeration value is 254, it indicates that environment temperature alarm resume; 
                  If the enumeration value is 255, it indicates environment temperature sensor operation status unknown. "
            ::= { hwEnvTempSensorEntry 99 }

        hwEnvTempFatherEquipname OBJECT-TYPE
            SYNTAX OCTET STRING
            MAX-ACCESS read-only
            STATUS current
            DESCRIPTION
                "Name of the parent device of the Environment temperature "
            ::= { hwEnvTempSensorEntry 11 }

        hwEnvTempSensorRowStatus OBJECT-TYPE
            SYNTAX RowStatus
            MAX-ACCESS read-create
            STATUS current
            DESCRIPTION
                "RowStatus of Environment temperature table."
            ::= { hwEnvTempSensorEntry 100 }

        hwEnvHumiSensorTable OBJECT-TYPE
            SYNTAX SEQUENCE OF HwEnvHumiSensorEntry
            MAX-ACCESS not-accessible
             STATUS current
             DESCRIPTION
                "Environment humidity table. Use this table to get environment humidity equipment ID , environment humidity equipment name, and environment humidity, set environment humidity upper limit, environment humidity lower limit, and environment humidity alarm enable. 
                This table's index is hwEnvHumiSensorIndex, which qualificated by hwEnvHumiSensorIndex, clone site environment humidity table."
            ::= { hwEnvSensor 2 }

        hwEnvHumiSensorEntry OBJECT-TYPE
                        SYNTAX HwEnvHumiSensorEntry
            MAX-ACCESS not-accessible
             STATUS current
             DESCRIPTION
                "Environment humidity table. Use this table to get environment humidity equipment ID , environment humidity equipment name, and environment humidity, set environment humidity upper limit, environment humidity lower limit, and environment humidity alarm enable. 
                This table's index is hwEnvHumiSensorIndex, which qualificated by hwEnvHumiSensorIndex, clone site environment humidity table."
            INDEX { hwEnvHumiSensorIndex }
            ::= { hwEnvHumiSensorTable 1 }

        HwEnvHumiSensorEntry            ::= SEQUENCE {
                hwEnvHumiSensorIndex
                    Integer32,
                hwEnvHumiEquipId
                    Unsigned32,
                hwEnvHumiEquipName
                    OCTET STRING,
                hwEnvHumidity
                    Integer32,
                hwSetEnvHumidityUpperLimit
                    Integer32,
                hwSetEnvHumidityLowerLimit
                    Integer32,
                hwEnvHumiFatherEquipname
                    OCTET STRING,
                hwEnvHumiSensorOperStatus
                    INTEGER
            }

        hwEnvHumiSensorIndex OBJECT-TYPE
            SYNTAX Integer32
            MAX-ACCESS read-only
            STATUS current
            DESCRIPTION
                "Table index of the environment humility sensors.
                "
            ::= { hwEnvHumiSensorEntry 1 }

        hwEnvHumiEquipId OBJECT-TYPE
            SYNTAX Unsigned32 (10001..10255)
            MAX-ACCESS read-only
            STATUS current
            DESCRIPTION
                "Environment humility sensor ID, can be configured by users. Value range: 010'001 to 010'255, in which the first digits indicate the device type and the last three digits indicate the device SN."
            ::= { hwEnvHumiSensorEntry 2 }

        hwEnvHumiEquipName OBJECT-TYPE
            SYNTAX OCTET STRING (SIZE (0..63))
            MAX-ACCESS read-write
            STATUS current
            DESCRIPTION
                "Environment humility sensor name, of the character string type, is used to specify an environment humility sensor. Users can configure it. Otherwise, the configured character can not be any other languages except English."
            ::= { hwEnvHumiSensorEntry 3 }

        hwEnvHumidity OBJECT-TYPE
            SYNTAX Integer32 (0..100)
            MAX-ACCESS read-only
            STATUS current
            DESCRIPTION
                "Environment humility. It is an environment parameter collected in real time. 
                Value range: 0 to 100, 
                units: %RH, 
                and the value is an integer (1). 
                If the value is 2147483647(0x7FFFFFFF), it indicates that the humidity sensor is not configured."
            ::= { hwEnvHumiSensorEntry 4 }

        hwSetEnvHumidityUpperLimit OBJECT-TYPE
            SYNTAX Integer32 (0..100)
            MAX-ACCESS read-write
            STATUS current
            DESCRIPTION
                "Upper threshold of the environment humility alarm, can be configured by users. 
                Value range: 0 to 100, 
                units: %RH, 
                and the value is an integer (1).  
                If the value is 2147483647(0x7FFFFFFF), it indicates that the value is invalid."
            ::= { hwEnvHumiSensorEntry 5 }

        hwSetEnvHumidityLowerLimit OBJECT-TYPE
            SYNTAX Integer32 (0..100)
            MAX-ACCESS read-write
            STATUS current
            DESCRIPTION
                "Lower threshold of the environment humility alarm, can be configured by users. 
                Value range: 0 to 100, 
                units: %RH, 
                and the value is an integer (1).  
                If the value is 2147483647(0x7FFFFFFF), it indicates that the value is invalid."
            ::= { hwEnvHumiSensorEntry 6 }

        hwEnvHumiFatherEquipname OBJECT-TYPE
            SYNTAX OCTET STRING
            MAX-ACCESS read-only
            STATUS current
            DESCRIPTION
                "Name of the parent device of the Humi equip"
            ::= { hwEnvHumiSensorEntry 10 }

        hwEnvHumiSensorOperStatus OBJECT-TYPE
            SYNTAX INTEGER
                {
                normal(1),
                humidityHigh(2),
                humidityLow(3),
                notInslot(4),
                alarmResume(254),
                unknown(255)
                }
            MAX-ACCESS read-only
            STATUS current
            DESCRIPTION
                "State of the site environment humidity sensor. It is an enumeration type: 
                  If the enumeration value is 1, it indicates that the site environment humidity sensor is in the normal state; 
                  If the enumeration value is 2, it indicates that the environment humidity sensor is over humidity; 
                  If the enumeration value is 3, it indicates that the environment humidity sensor is under humidity;
                  If the enumeration value is 4, it indicates that the environment humidity sensor is not in slot;
                  If the enumeration value is 254, it indicates that environment humidity alarm resume;   
                  If the enumeration value is 255, it indicates environment humidity sensor operation status unknown.  "
            ::= { hwEnvHumiSensorEntry 99 }

        hwSpareDigitalTable OBJECT-TYPE
            SYNTAX SEQUENCE OF HwSpareDigitalEntry
            MAX-ACCESS not-accessible
             STATUS current
             DESCRIPTION
                "Spare digital table. Use this table to get Spare digital equipment ID , Spare digital equipment name, and current Spare digital alarm tension, ae well as to set Spare digital alarm enable. This table's index is hwSpareDigitalIndex, which qualificated by hwSpareDigitalsTotalQuantity, clone switch input table."
            ::= { hwEnvSensor 3 }

        hwSpareDigitalEntry OBJECT-TYPE
                        SYNTAX HwSpareDigitalEntry
            MAX-ACCESS not-accessible
             STATUS current
             DESCRIPTION
                "Spare digital table. Use this table to get Spare digital equipment ID , Spare digital equipment name, and current Spare digital alarm tension, ae well as to set Spare digital alarm enable. This table's index is hwSpareDigitalIndex, which qualificated by hwSpareDigitalsTotalQuantity, clone switch input table."
            INDEX { hwSpareDigitalIndex }
            ::= { hwSpareDigitalTable 1 }

        HwSpareDigitalEntry            ::= SEQUENCE {
                hwSpareDigitalIndex
                    Integer32,
                hwSpareDigitalEquipId
                    Unsigned32,
                hwSpareDigitalEquipName
                    OCTET STRING,
                hwSpareDigitalAlarmTension
                    INTEGER,
                hwSpareDigitalFatherEquipname
                    OCTET STRING,
                hwSpareDigitalOperStatus
                    INTEGER
            }

        hwSpareDigitalIndex OBJECT-TYPE
            SYNTAX Integer32 (1..256)
            MAX-ACCESS read-only
            STATUS current
            DESCRIPTION
                "Spare digital table index, which 
                value range: 1 to 256. 
                Lines of the device list are restricted by the quantity of Spare digitals (hwSpareDigitalsTotalQuantity). "
            ::= { hwSpareDigitalEntry 1 }

        hwSpareDigitalEquipId OBJECT-TYPE
            SYNTAX Unsigned32
            MAX-ACCESS read-only
            STATUS current
            DESCRIPTION
                "Spare digital device ID. "
            ::= { hwSpareDigitalEntry 2 }

        hwSpareDigitalEquipName OBJECT-TYPE
            SYNTAX OCTET STRING (SIZE (0..8))
            MAX-ACCESS read-only
            STATUS current
            DESCRIPTION
                "Spare digital name, of the character string type, is used to specify Spare digitals. Users can configure it. Otherwise, the configured character can not be any other languages except English."
            ::= { hwSpareDigitalEntry 3 }

        hwSpareDigitalAlarmTension OBJECT-TYPE
            SYNTAX INTEGER
                {
                open(0),
                close(1)
                }
            MAX-ACCESS read-write
            STATUS current
            DESCRIPTION
                "Spare digital alarm state. It is an enumeration value.  
                  If the value of the node is open, it indicates a low-tension alarm;
                  If the value of the node is close, it indicates a high-tension alarm. "
            ::= { hwSpareDigitalEntry 4 }

        hwSpareDigitalFatherEquipname OBJECT-TYPE
            SYNTAX OCTET STRING
            MAX-ACCESS read-only
            STATUS current
            DESCRIPTION
                "Name of the parent device of the Spare digital"
            ::= { hwSpareDigitalEntry 6 }

        hwSpareDigitalOperStatus OBJECT-TYPE
            SYNTAX INTEGER
                {
                normal(1),
                alarm(2),
                alarmResume(254),
                unknown(255)
                }
            MAX-ACCESS read-only
            STATUS current
            DESCRIPTION
                "State of the site Spare digital. It is an enumeration type: 
                  If the enumeration value is 1, it indicates that the Spare digital operation state is normal; 
                  If the enumeration value is 2, it indicates that a alarm occurs on the Spare digital;  
                  If the enumeration value is 254, it indicates that spare digital alarm resume;  
                  If the enumeration value is 255, it indicates Spare digital operation status unknown."
            ::= { hwSpareDigitalEntry 99 }

        hwSpareDigitalOutputTable OBJECT-TYPE
            SYNTAX SEQUENCE OF HwSpareDigitalOutputEntry
            MAX-ACCESS not-accessible
             STATUS current
             DESCRIPTION
                "Spare digital table. Use this table to get Spare digital equipment ID , Spare digital equipment name, and current Spare digital alarm tension, ae well as to set Spare digital alarm enable. This table's index is hwSpareDigitalIndex, which qualificated by hwSpareDigitalsTotalQuantity, clone switch input table."
            ::= { hwEnvSensor 4 }

        hwSpareDigitalOutputEntry OBJECT-TYPE
                        SYNTAX HwSpareDigitalOutputEntry
            MAX-ACCESS not-accessible
             STATUS current
             DESCRIPTION
                "Spare digital table. Use this table to get Spare digital equipment ID , Spare digital equipment name, and current Spare digital alarm tension, ae well as to set Spare digital alarm enable. This table's index is hwSpareDigitalIndex, which qualificated by hwSpareDigitalsTotalQuantity, clone switch input table."
            INDEX { hwSpareDigitalOutputIndex }
            ::= { hwSpareDigitalOutputTable 1 }

        HwSpareDigitalOutputEntry            ::= SEQUENCE {
                hwSpareDigitalOutputIndex
                    Integer32,
                hwSpareDigitalOutputEquipId
                    Unsigned32,
                hwSpareDigitalOutputEquipName
                    OCTET STRING,
                hwSetSpareDigitalOutputAlarmCondition
                    INTEGER,
                hwSpareDigitalOutputFatherEquipname
                    OCTET STRING,
                hwSpareDigitalOutputOperStatus
                    INTEGER
            }

        hwSpareDigitalOutputIndex OBJECT-TYPE
            SYNTAX Integer32 (1..256)
            MAX-ACCESS read-only
            STATUS current
            DESCRIPTION
                "Spare digital table index, which 
                value range: 1 to 256. 
                Lines of the device list are restricted by the quantity of Spare digitals (hwSpareDigitalsTotalQuantity). "
            ::= { hwSpareDigitalOutputEntry 1 }

        hwSpareDigitalOutputEquipId OBJECT-TYPE
            SYNTAX Unsigned32
            MAX-ACCESS read-only
            STATUS current
            DESCRIPTION
                "Spare digital output device ID. "
            ::= { hwSpareDigitalOutputEntry 2 }

        hwSpareDigitalOutputEquipName OBJECT-TYPE
            SYNTAX OCTET STRING (SIZE (0..63))
            MAX-ACCESS read-only
            STATUS current
            DESCRIPTION
                "Spare digital name, of the character string type, is used to specify Spare digitals. Users can configure it. Otherwise, the configured character can not be any other languages except English. "
            ::= { hwSpareDigitalOutputEntry 3 }

        hwSetSpareDigitalOutputAlarmCondition OBJECT-TYPE
            SYNTAX INTEGER
                {
                open(1),
                close(2)
                }
            MAX-ACCESS read-write
            STATUS current
            DESCRIPTION
                "Spare digital alarm state. It is an enumeration value.  
                  If the value of the node is 1, it indicates a low-tension alarm;
                  If the value of the node is 2, it indicates a high-tension alarm. "
            ::= { hwSpareDigitalOutputEntry 4 }

        hwSpareDigitalOutputFatherEquipname OBJECT-TYPE
            SYNTAX OCTET STRING
            MAX-ACCESS read-only
            STATUS current
            DESCRIPTION
                "Name of the parent device of the Spare digital output "
            ::= { hwSpareDigitalOutputEntry 6 }

        hwSpareDigitalOutputOperStatus OBJECT-TYPE
            SYNTAX INTEGER
                {
                open(1),
                close(2),
                unknown(255)
                }
            MAX-ACCESS read-only
            STATUS current
            DESCRIPTION
                "State of the site Spare digital. It is an enumeration type: 
                  If the enumeration value is 1, it indicates that the Spare digital operation state is normal; 
                  If the enumeration value is 2, it indicates that a alarm occurs on the Spare digital;  
                  If the enumeration value is 255, it indicates Spare digital operation status unknown."
            ::= { hwSpareDigitalOutputEntry 99 }

        hwTemp1Table OBJECT-TYPE
            SYNTAX SEQUENCE OF HwTemp1Entry
            MAX-ACCESS not-accessible
             STATUS current
             DESCRIPTION
                "Temp1 Table."
            ::= { hwEnvSensor 5 }

        hwTemp1Entry OBJECT-TYPE
                        SYNTAX HwTemp1Entry
            MAX-ACCESS not-accessible
             STATUS current
             DESCRIPTION
                "Temp1 Table."
            INDEX { hwTemp1Index }
            ::= { hwTemp1Table 1 }

        HwTemp1Entry            ::= SEQUENCE {
                hwTemp1Index
                    Integer32,
                hwTemp1EquipId
                    Unsigned32,
                hwTemp1EquipName
                    OCTET STRING,
                hwTemp1Value
                    Integer32,
                hwTemp1HighLimit
                    Integer32,
                hwTemp1LowLimit
                    Integer32,
                hwTemp1FatherEquipname
                    OCTET STRING,
                hwTemp1OperStatus
                    INTEGER
            }

        hwTemp1Index OBJECT-TYPE
            SYNTAX Integer32 (3394)
            MAX-ACCESS read-only
            STATUS current
            DESCRIPTION
                "Table index of the temp1 sensors. Value range: 1 to 256. Lines of the device list are restricted by the quantity of temp1 sensors (hwEnvHumiSensorsTotalQuantity). "
            ::= { hwTemp1Entry 1 }

        hwTemp1EquipId OBJECT-TYPE
            SYNTAX Unsigned32 (26000..26255)
            MAX-ACCESS read-only
            STATUS current
            DESCRIPTION
                "Temp1 sensor ID, can be configured by users. Value range: 026'000 to 026'255, in which the first digits indicate the device type and the last three digits indicate the device SN."
            ::= { hwTemp1Entry 2 }

        hwTemp1EquipName OBJECT-TYPE
            SYNTAX OCTET STRING (SIZE (0..63))
            MAX-ACCESS read-only
            STATUS current
            DESCRIPTION
                "Temp1 sensor name, of the character string type, is used to specify an temp1 sensor. Users can configure it. Otherwise, the configured character can not be any other languages except English."
            ::= { hwTemp1Entry 3 }

        hwTemp1Value OBJECT-TYPE
            SYNTAX Integer32 ( -40..80)
            MAX-ACCESS read-only
            STATUS current
            DESCRIPTION
                "Temp1. It is an environment parameter collected in real time. 
                Value range: -40 to +80, 
                units: centigrade (degC), 
                and the value is an integer (1).  
                If the value is -1024, it indicates that the temperature sensor is not configured."
            ::= { hwTemp1Entry 4 }

        hwTemp1HighLimit OBJECT-TYPE
            SYNTAX Integer32 (25..80)
            MAX-ACCESS read-write
            STATUS current
            DESCRIPTION
                "Upper threshold of the temp1 alarm, can be configured by users. 
                Value range: 25 to 80, 
                units: centigrade (degC), 
                and the value is an integer (1).  
                If the value is 2147483647(0x7FFFFFFF), it indicates that the value is invalid."
            ::= { hwTemp1Entry 5 }

        hwTemp1LowLimit OBJECT-TYPE
            SYNTAX Integer32 ( -20..20)
            MAX-ACCESS read-write
            STATUS current
            DESCRIPTION
                "Lower threshold of the temp1 alarm, can be configured by users. Value range: -20 to 20, units: centigrade (degC), and the value is an integer (1).  If the value is 2147483647(0x7FFFFFFF), it indicates that the value is invalid."
            ::= { hwTemp1Entry 6 }

        hwTemp1FatherEquipname OBJECT-TYPE
            SYNTAX OCTET STRING
            MAX-ACCESS read-only
            STATUS current
            DESCRIPTION
                "Name of the parent device of the Temp1 sensors"
            ::= { hwTemp1Entry 7 }

        hwTemp1OperStatus OBJECT-TYPE
            SYNTAX INTEGER
                {
                normal(1),
                tempHigh(2),
                tempLow(3),
                notInslot(4),
                tempFault(5),
                alarmResume(254),
                unknown(255)
                }
            MAX-ACCESS read-only
            STATUS current
            DESCRIPTION
                "State of the site temp1 sensor. It is an enumeration type: 
                  If the enumeration value is 1, it indicates that the site temp1 sensor is in the normal state; 
                  If the enumeration value is 2, it indicates that the temp1 sensor is over temperature; 
                  If the enumeration value is 3, it indicates that the temp1 sensor is under temperature; 
                  If the enumeration value is 4, it indicates that the temp1 sensor is not in slot;
                  If the enumeration value is 5, it indicates that the temp1 sensor is fault;
                  If the enumeration value is 254, it indicates that temp1 alarm resume; 
                  If the enumeration value is 255, it indicates temp1 sensor operation status unknown."
            ::= { hwTemp1Entry 99 }

        hwTemp2Table OBJECT-TYPE
            SYNTAX SEQUENCE OF HwTemp2Entry
            MAX-ACCESS not-accessible
             STATUS current
             DESCRIPTION
                "Temp2 Table."
            ::= { hwEnvSensor 6 }

        hwTemp2Entry OBJECT-TYPE
                        SYNTAX HwTemp2Entry
            MAX-ACCESS not-accessible
             STATUS current
             DESCRIPTION
                "Temp2 Table."
            INDEX { hwTemp2Index }
            ::= { hwTemp2Table 1 }

        HwTemp2Entry            ::= SEQUENCE {
                hwTemp2Index
                    Integer32,
                hwTemp2EquipId
                    Unsigned32,
                hwTemp2EquipName
                    OCTET STRING,
                hwTemp2Value
                    Integer32,
                hwTemp2HighLimit
                    Integer32,
                hwTemp2LowLimit
                    Integer32,
                hwTemp2FatherEquipname
                    OCTET STRING,
                hwTemp2OperStatus
                    INTEGER
            }

        hwTemp2Index OBJECT-TYPE
            SYNTAX Integer32 (3394)
            MAX-ACCESS read-only
            STATUS current
            DESCRIPTION
                "Table index of the temp2 sensors. 
                Value range: 1 to 256. 
                Lines of the device list are restricted by the quantity of temp2 sensors (hwEnvHumiSensorsTotalQuantity). "
            ::= { hwTemp2Entry 1 }

        hwTemp2EquipId OBJECT-TYPE
            SYNTAX Unsigned32 (27000..27255)
            MAX-ACCESS read-only
            STATUS current
            DESCRIPTION
                "Temp2 sensor ID, can be configured by users. Value range: 027'000 to 027'255, in which the first digits indicate the device type and the last three digits indicate the device SN."
            ::= { hwTemp2Entry 2 }

        hwTemp2EquipName OBJECT-TYPE
            SYNTAX OCTET STRING (SIZE (0..63))
            MAX-ACCESS read-only
            STATUS current
            DESCRIPTION
                "Temp2 sensor name, of the character string type, is used to specify an temp2 sensor. Users can configure it. Otherwise, the configured character can not be any other languages except English."
            ::= { hwTemp2Entry 3 }

        hwTemp2Value OBJECT-TYPE
            SYNTAX Integer32 ( -40..80)
            MAX-ACCESS read-only
            STATUS current
            DESCRIPTION
                "Temp2. It is an environment parameter collected in real time. 
                Value range: -40 to +80, 
                units: centigrade (degC), 
                and the value is an integer (1).  
                If the value is -1024, it indicates that the temperature sensor is not configured."
            ::= { hwTemp2Entry 4 }

        hwTemp2HighLimit OBJECT-TYPE
            SYNTAX Integer32 (25..80)
            MAX-ACCESS read-write
            STATUS current
            DESCRIPTION
                "Upper threshold of the temp2 alarm, can be configured by users. 
                Value range: 25 to 80, 
                units: centigrade (degC), 
                and the value is an integer (1).  
                If the value is 2147483647(0x7FFFFFFF), it indicates that the value is invalid."
            ::= { hwTemp2Entry 5 }

        hwTemp2LowLimit OBJECT-TYPE
            SYNTAX Integer32 ( -20..20)
            MAX-ACCESS read-write
            STATUS current
            DESCRIPTION
                "Lower threshold of the temp2 alarm, can be configured by users. 
                Value range: -20 to 20, 
                units: centigrade (degC), 
                and the value is an integer (1).  
                If the value is 2147483647(0x7FFFFFFF), it indicates that the value is invalid."
            ::= { hwTemp2Entry 6 }

        hwTemp2FatherEquipname OBJECT-TYPE
            SYNTAX OCTET STRING
            MAX-ACCESS read-only
            STATUS current
            DESCRIPTION
                "Name of the parent device of the Temp2 sensors"
            ::= { hwTemp2Entry 7 }

        hwTemp2OperStatus OBJECT-TYPE
            SYNTAX INTEGER
                {
                normal(1),
                tempHigh(2),
                tempLow(3),
                notInslot(4),
                tempFault(5),
                alarmResume(254),
                unknown(255)
                }
            MAX-ACCESS read-only
            STATUS current
            DESCRIPTION
                "State of the site temp2 sensor. It is an enumeration type: 
                  If the enumeration value is 1, it indicates that the site temp2 sensor is in the normal state; 
                  If the enumeration value is 2, it indicates that the temp2 sensor is over temperature; 
                  If the enumeration value is 3, it indicates that the temp2 sensor is under temperature; 
                  If the enumeration value is 4, it indicates that the temp2 sensor is not in slot;
                  If the enumeration value is 5, it indicates that the temp2 sensor is fault;
                  If the enumeration value is 254, it indicates that temp2 alarm resume; 
                  If the enumeration value is 255, it indicates temp2 sensor operation status unknown."
            ::= { hwTemp2Entry 99 }

        hwSmokeSensorTable OBJECT-TYPE
            SYNTAX SEQUENCE OF HwSmokeSensorEntry
            MAX-ACCESS not-accessible
             STATUS current
             DESCRIPTION
                "/"
            ::= { hwEnvSensor 13 }

        hwSmokeSensorEntry OBJECT-TYPE
                        SYNTAX HwSmokeSensorEntry
            MAX-ACCESS not-accessible
             STATUS current
             DESCRIPTION
                "/"
            INDEX { hwSmokeSensorIndex }
            ::= { hwSmokeSensorTable 1 }

        HwSmokeSensorEntry            ::= SEQUENCE {
                hwSmokeSensorIndex
                    Unsigned32,
                hwSmokeSensorEquipId
                    Unsigned32,
                hwSmokeEquipName
                    OCTET STRING,
                hwSmokeSensorStatus
                    INTEGER,
                hwSmokeSensorFatherEquipname
                    OCTET STRING,
                hwSmokeSensorReset
                    INTEGER
            }

        hwSmokeSensorIndex OBJECT-TYPE
            SYNTAX Unsigned32
            MAX-ACCESS read-only
            STATUS current
            DESCRIPTION
                "The tem_hum equip Index."
            ::= { hwSmokeSensorEntry 1 }

        hwSmokeSensorEquipId OBJECT-TYPE
            SYNTAX Unsigned32
            MAX-ACCESS read-only
            STATUS current
            DESCRIPTION
                "/"
            ::= { hwSmokeSensorEntry 2 }

        hwSmokeEquipName OBJECT-TYPE
            SYNTAX OCTET STRING (SIZE (0..63))
            MAX-ACCESS read-only
            STATUS current
            DESCRIPTION
                "/"
            ::= { hwSmokeSensorEntry 3 }

        hwSmokeSensorStatus OBJECT-TYPE
            SYNTAX INTEGER
                {
                normal(0),
                alarm(1)
                }
            MAX-ACCESS read-only
            STATUS current
            DESCRIPTION
                "The smoke sensor status"
            ::= { hwSmokeSensorEntry 4 }

        hwSmokeSensorFatherEquipname OBJECT-TYPE
            SYNTAX OCTET STRING
            MAX-ACCESS read-only
            STATUS current
            DESCRIPTION
                "Name of the parent device of the Smoke Sensor"
            ::= { hwSmokeSensorEntry 5 }

        hwSmokeSensorReset OBJECT-TYPE
            SYNTAX INTEGER
                {
                normal(1),
                reset(2),
                nullOper(255)
                }
            MAX-ACCESS read-write
            STATUS current
            DESCRIPTION
                "Smoke sensor reset. It manually controls clearance of the smoke sensor alarm, and this node is of the enumeration type. 
                If the enumeration value of the node is 1, it indicates that the reset of the smoke sensor is not required. 
                If the enumeration value of the node is 2, it indicates that the background controls the reset of the smoke sensor. 
                If the enumeration value of the node is 255, it indicates that the background controls the unknown of the smoke sensor. "
            ::= { hwSmokeSensorEntry 6 }

        hwWaterSensorTable OBJECT-TYPE
            SYNTAX SEQUENCE OF HwWaterSensorEntry
            MAX-ACCESS not-accessible
             STATUS current
             DESCRIPTION
                "/"
            ::= { hwEnvSensor 14 }

        hwWaterSensorEntry OBJECT-TYPE
                        SYNTAX HwWaterSensorEntry
            MAX-ACCESS not-accessible
             STATUS current
             DESCRIPTION
                "/"
            INDEX { hwWaterSensorIndex }
            ::= { hwWaterSensorTable 1 }

        HwWaterSensorEntry            ::= SEQUENCE {
                hwWaterSensorIndex
                    Unsigned32,
                hwWaterSensorEquipId
                    Unsigned32,
                hwWaterEquipName
                    OCTET STRING,
                hwWaterSensorStatus
                    INTEGER,
                hwWaterSensorFatherEquipname
                    OCTET STRING
            }

        hwWaterSensorIndex OBJECT-TYPE
            SYNTAX Unsigned32
            MAX-ACCESS read-only
            STATUS current
            DESCRIPTION
                "The tem_hum equip Index."
            ::= { hwWaterSensorEntry 1 }

        hwWaterSensorEquipId OBJECT-TYPE
            SYNTAX Unsigned32
            MAX-ACCESS read-only
            STATUS current
            DESCRIPTION
                "/"
            ::= { hwWaterSensorEntry 2 }

        hwWaterEquipName OBJECT-TYPE
            SYNTAX OCTET STRING (SIZE (0..63))
            MAX-ACCESS read-only
            STATUS current
            DESCRIPTION
                "/"
            ::= { hwWaterSensorEntry 3 }

        hwWaterSensorStatus OBJECT-TYPE
            SYNTAX INTEGER
                {
                normal(0),
                alarm(1)
                }
            MAX-ACCESS read-only
            STATUS current
            DESCRIPTION
                "The smoke sensor status"
            ::= { hwWaterSensorEntry 4 }

        hwWaterSensorFatherEquipname OBJECT-TYPE
            SYNTAX OCTET STRING
            MAX-ACCESS read-only
            STATUS current
            DESCRIPTION
                "Name of the parent device of the Water Sensor"
            ::= { hwWaterSensorEntry 5 }

        hwDoorSensorTable OBJECT-TYPE
            SYNTAX SEQUENCE OF HwDoorSensorEntry
            MAX-ACCESS not-accessible
             STATUS current
             DESCRIPTION
                "/"
            ::= { hwEnvSensor 15 }

        hwDoorSensorEntry OBJECT-TYPE
                        SYNTAX HwDoorSensorEntry
            MAX-ACCESS not-accessible
             STATUS current
             DESCRIPTION
                "/"
            INDEX { hwDoorSensorIndex }
            ::= { hwDoorSensorTable 1 }

        HwDoorSensorEntry            ::= SEQUENCE {
                hwDoorSensorIndex
                    Unsigned32,
                hwDoorSensorEquipId
                    Unsigned32,
                hwDoorEquipName
                    OCTET STRING,
                hwDoorSensorStatus
                    INTEGER,
                hwDoorSensorFatherEquipname
                    OCTET STRING
            }

        hwDoorSensorIndex OBJECT-TYPE
            SYNTAX Unsigned32
            MAX-ACCESS read-only
            STATUS current
            DESCRIPTION
                "The tem_hum equip Index."
            ::= { hwDoorSensorEntry 1 }

        hwDoorSensorEquipId OBJECT-TYPE
            SYNTAX Unsigned32
            MAX-ACCESS read-only
            STATUS current
            DESCRIPTION
                "/"
            ::= { hwDoorSensorEntry 2 }

        hwDoorEquipName OBJECT-TYPE
            SYNTAX OCTET STRING (SIZE (0..63))
            MAX-ACCESS read-only
            STATUS current
            DESCRIPTION
                "/"
            ::= { hwDoorSensorEntry 3 }

        hwDoorSensorStatus OBJECT-TYPE
            SYNTAX INTEGER
                {
                normal(0),
                alarm(1)
                }
            MAX-ACCESS read-only
            STATUS current
            DESCRIPTION
                "The smoke sensor status"
            ::= { hwDoorSensorEntry 4 }

        hwDoorSensorFatherEquipname OBJECT-TYPE
            SYNTAX OCTET STRING
            MAX-ACCESS read-only
            STATUS current
            DESCRIPTION
                "Name of the parent device of the Door Sensor "
            ::= { hwDoorSensorEntry 5 }

        hwSiteInverters OBJECT IDENTIFIER ::= { hwSiteMonitorMIBObjects 9 }

        hwInverterGroup OBJECT IDENTIFIER ::= { hwSiteInverters 1 }

        hwInverterGroupId OBJECT-TYPE
            SYNTAX Unsigned32
            MAX-ACCESS read-only
            STATUS current
            DESCRIPTION
                "Inverter unit group ID. It is the unique ID of the Inverter unit group. 
                The first digits indicate the device type. The last three digits indicate the device SN. 
                If the last three digits are 000, it indicates a virtual device."
            ::= { hwInverterGroup 1 }

        hwInverterGroupName OBJECT-TYPE
            SYNTAX Unsigned32 (0..63
)
            MAX-ACCESS read-write
            STATUS current
            DESCRIPTION
                "Inverter unit group name, of the character string type, can be configured by users.Otherwise, the configured character can not be any other languages except English."
            ::= { hwInverterGroup 2 }

        hwInverterQuantity OBJECT-TYPE
            SYNTAX Unsigned32
            MAX-ACCESS read-only
            STATUS current
            DESCRIPTION
                "Total site intelligent Inverters. "
            ::= { hwInverterGroup 3 }

        hwInverter OBJECT IDENTIFIER ::= { hwSiteInverters 2 }

        hwInverterTable OBJECT-TYPE
            SYNTAX SEQUENCE OF HwInverterEntry
            MAX-ACCESS not-accessible
             STATUS current
             DESCRIPTION
                "/"
            ::= { hwInverter 1 }

        hwInverterEntry OBJECT-TYPE
                        SYNTAX HwInverterEntry
            MAX-ACCESS not-accessible
             STATUS current
             DESCRIPTION
                "/"
            INDEX { hwInverterIndex }
            ::= { hwInverterTable 1 }

        HwInverterEntry            ::= SEQUENCE {
                hwInverterIndex
                    Unsigned32,
                hwInverterEquipId
                    Unsigned32,
                hwInverterEquipName
                    OCTET STRING,
                hwInverterAcOutputVolt
                    Unsigned32,
                hwInverterAcOutputCurr
                    Unsigned32,
                hwInverterAcOutputFreq
                    Unsigned32,
                hwInverterAcOutputActivePower
                    Unsigned32,
                hwInverterAcOutputVA
                    Unsigned32,
                hwInverterAcInputVolt
                    Unsigned32,
                hwInverterAcInputCurr
                    Unsigned32,
                hwInverterAcInputFreq
                    Unsigned32,
                hwInverterAcInputActivePower
                    Unsigned32,
                hwInverterAcInputVA
                    Unsigned32,
                hwInverterDcInputVolt
                    Unsigned32,
                hwInverterDcInputCurr
                    Unsigned32,
                hwInverterDcInputPower
                    Unsigned32,
                hwInverterRevision
                    OCTET STRING,
                hwInverterPhaseNum
                    Unsigned32,
                hwInverterAcGroupNum
                    Unsigned32,
                hwInverterDcGroupNum
                    Unsigned32,
                hwInverterMajorAlarmNum
                    Unsigned32,
                hwInverterMinorAlarmNum
                    Unsigned32,
                hwInverterT2SSerialNum
                    Unsigned32,
                hwInverterModuleTemp
                    Integer32,
                hwInverterOperStatus
                    INTEGER,
                hwInverterRowStatus
                    RowStatus
            }

        hwInverterIndex OBJECT-TYPE
            SYNTAX Unsigned32 (1..256)
            MAX-ACCESS read-only
            STATUS current
            DESCRIPTION
                "Inverter table index,which value range:1 to 256.Lines of the device list are restricted by the quantity of Inverter."
            ::= { hwInverterEntry 1 }

        hwInverterEquipId OBJECT-TYPE
            SYNTAX Unsigned32 (18001..18255)
            MAX-ACCESS read-only
            STATUS current
            DESCRIPTION
                "Inverter device ID. Value range: 018'001 to 018'255, in which the first digits indicate the device type and the last three digits indicate the device SN. "
            ::= { hwInverterEntry 2 }

        hwInverterEquipName OBJECT-TYPE
            SYNTAX OCTET STRING (SIZE (0..63))
            MAX-ACCESS read-only
            STATUS current
            DESCRIPTION
                "Inverter name, of the character string type, is used to specify Inverters. Users can configure it.Otherwise, the configured character can not be any other languages except English. "
            ::= { hwInverterEntry 3 }

        hwInverterAcOutputVolt OBJECT-TYPE
            SYNTAX Unsigned32 (0..100000)
            MAX-ACCESS read-only
            STATUS current
            DESCRIPTION
                "Inverter AC Output voltage, 
                Value range: 0.0 to 10000.0.
                Unit: V.
                and the value is accurate to one decimal space (.1).  
                If the value is 2147483647(0x7FFFFFFF), it indicates that the value is invalid."
            ::= { hwInverterEntry 4 }

        hwInverterAcOutputCurr OBJECT-TYPE
            SYNTAX Unsigned32 (0..100000)
            MAX-ACCESS read-only
            STATUS current
            DESCRIPTION
                "Inverter AC Output current, 
                Value range: 0.0 to 10000.0.
                Unit: A.
                and the value is accurate to one decimal space (.1).  
                If the value is 2147483647(0x7FFFFFFF), it indicates that the value is invalid."
            ::= { hwInverterEntry 5 }

        hwInverterAcOutputFreq OBJECT-TYPE
            SYNTAX Unsigned32 (0..10000)
            MAX-ACCESS read-only
            STATUS current
            DESCRIPTION
                "Inverter AC Output frequency, 
                Value range: 0 to 10000. 
                Unit: Hz. 
                If the value is 2147483647(0x7FFFFFFF), it indicates that the value is invalid."
            ::= { hwInverterEntry 6 }

        hwInverterAcOutputActivePower OBJECT-TYPE
            SYNTAX Unsigned32 (0..10000000)
            MAX-ACCESS read-only
            STATUS current
            DESCRIPTION
                "Inverter AC Output power, 
                Value range: 0 to 10000000.
                Unit: W. 
                If the value is 2147483647(0x7FFFFFFF), it indicates that the value is invalid."
            ::= { hwInverterEntry 7 }

        hwInverterAcOutputVA OBJECT-TYPE
            SYNTAX Unsigned32 (0..100000)
            MAX-ACCESS read-only
            STATUS current
            DESCRIPTION
                "Inverter AC Output power, 
                Value range: 0.0 to 100000.0.
                Unit: VA.
                and the value is accurate to one decimal space (.1).  
                If the value is 2147483647(0x7FFFFFFF), it indicates that the value is invalid."
            ::= { hwInverterEntry 8 }

        hwInverterAcInputVolt OBJECT-TYPE
            SYNTAX Unsigned32 (0..100000)
            MAX-ACCESS read-only
            STATUS current
            DESCRIPTION
                "Inverter AC Input voltage, 
                Value range: 0.0 to 10000.0.
                Unit: V.
                and the value is accurate to one decimal space (.1).  
                If the value is 2147483647(0x7FFFFFFF), it indicates that the value is invalid."
            ::= { hwInverterEntry 9 }

        hwInverterAcInputCurr OBJECT-TYPE
            SYNTAX Unsigned32 (0..100000)
            MAX-ACCESS read-only
            STATUS current
            DESCRIPTION
                "Inverter AC Input current, 
                Value range: 0.0 to 10000.0.
                Unit: A.
                and the value is accurate to one decimal space (.1).  
                If the value is 2147483647(0x7FFFFFFF), it indicates that the value is invalid."
            ::= { hwInverterEntry 10 }

        hwInverterAcInputFreq OBJECT-TYPE
            SYNTAX Unsigned32 (0..10000)
            MAX-ACCESS read-only
            STATUS current
            DESCRIPTION
                "Inverter AC Input frequency, 
                Value range: 0 to 10000. 
                Unit: Hz. 
                If the value is 2147483647(0x7FFFFFFF), it indicates that the value is invalid."
            ::= { hwInverterEntry 11 }

        hwInverterAcInputActivePower OBJECT-TYPE
            SYNTAX Unsigned32 (0..10000000)
            MAX-ACCESS read-only
            STATUS current
            DESCRIPTION
                "Inverter AC Input power, 
                Value range: 0 to 10000000.
                Unit: W. 
                If the value is 2147483647(0x7FFFFFFF), it indicates that the value is invalid."
            ::= { hwInverterEntry 12 }

        hwInverterAcInputVA OBJECT-TYPE
            SYNTAX Unsigned32 (0..100000)
            MAX-ACCESS read-only
            STATUS current
            DESCRIPTION
                "Inverter AC Input power, 
                Value range: 0.0 to 10000.0.
                Unit: VA.
                and the value is accurate to one decimal space (.1).  
                If the value is 2147483647(0x7FFFFFFF), it indicates that the value is invalid."
            ::= { hwInverterEntry 13 }

        hwInverterDcInputVolt OBJECT-TYPE
            SYNTAX Unsigned32 (0..100000)
            MAX-ACCESS read-only
            STATUS current
            DESCRIPTION
                "Inverter DC Input voltage, 
                Value range: 0.0 to 10000.0.
                Unit: V.
                and the value is accurate to one decimal space (.1).  
                If the value is 2147483647(0x7FFFFFFF), it indicates that the value is invalid."
            ::= { hwInverterEntry 14 }

        hwInverterDcInputCurr OBJECT-TYPE
            SYNTAX Unsigned32 (0..100000)
            MAX-ACCESS read-only
            STATUS current
            DESCRIPTION
                "Inverter DC Input current, 
                Value range: 0 to 10000. 
                Unit: A.
                and the value is accurate to one decimal space (.1).  
                If the value is 2147483647(0x7FFFFFFF), it indicates that the value is invalid."
            ::= { hwInverterEntry 15 }

        hwInverterDcInputPower OBJECT-TYPE
            SYNTAX Unsigned32 (0..10000000)
            MAX-ACCESS read-only
            STATUS current
            DESCRIPTION
                "Inverter DC Input power, 
                Value range: 0 to 10000000.
                Unit: W. 
                If the value is 2147483647(0x7FFFFFFF), it indicates that the value is invalid."
            ::= { hwInverterEntry 16 }

        hwInverterRevision OBJECT-TYPE
            SYNTAX OCTET STRING (SIZE (0..63))
            MAX-ACCESS read-only
            STATUS current
            DESCRIPTION
                "Inverter software version number."
            ::= { hwInverterEntry 17 }

        hwInverterPhaseNum OBJECT-TYPE
            SYNTAX Unsigned32 (0..10000)
            MAX-ACCESS read-only
            STATUS current
            DESCRIPTION
                "Inverter Number of the phase module, Value range: 0 to 10000.   If the value is 2147483647(0x7FFFFFFF), it indicates that the value is invalid."
            ::= { hwInverterEntry 18 }

        hwInverterAcGroupNum OBJECT-TYPE
            SYNTAX Unsigned32 (0..10000)
            MAX-ACCESS read-only
            STATUS current
            DESCRIPTION
                "Inverter Number of AC group, 
                Value range: 0 to 10000.  
                If the value is 2147483647(0x7FFFFFFF), it indicates that the value is invalid."
            ::= { hwInverterEntry 19 }

        hwInverterDcGroupNum OBJECT-TYPE
            SYNTAX Unsigned32 (0..10000)
            MAX-ACCESS read-only
            STATUS current
            DESCRIPTION
                "Inverter Number of DC group, 
                Value range: 0 to 10000.  
                If the value is 2147483647(0x7FFFFFFF), it indicates that the value is invalid."
            ::= { hwInverterEntry 20 }

        hwInverterMajorAlarmNum OBJECT-TYPE
            SYNTAX Unsigned32 (0..10000)
            MAX-ACCESS read-only
            STATUS current
            DESCRIPTION
                "Inverter Number of Major alarm, 
                Value range: 0 to 10000.  
                If the value is 2147483647(0x7FFFFFFF), it indicates that the value is invalid."
            ::= { hwInverterEntry 21 }

        hwInverterMinorAlarmNum OBJECT-TYPE
            SYNTAX Unsigned32 (0..10000)
            MAX-ACCESS read-only
            STATUS current
            DESCRIPTION
                "Inverter Number of Minor alarm, 
                Value range: 0 to 10000.  
                If the value is 2147483647(0x7FFFFFFF), it indicates that the value is invalid."
            ::= { hwInverterEntry 22 }

        hwInverterT2SSerialNum OBJECT-TYPE
            SYNTAX Unsigned32 (0..4294967295)
            MAX-ACCESS read-only
            STATUS current
            DESCRIPTION
                "Inverter T2S serial number, 
                Value range: 0 to 4294967295.  
                If the value is 4294967295(0x7FFFFFFF), it indicates that the value is invalid."
            ::= { hwInverterEntry 23 }

        hwInverterModuleTemp OBJECT-TYPE
            SYNTAX Integer32 (-300..10000)
            MAX-ACCESS read-only
            STATUS current
            DESCRIPTION
                "Inverter module Temperature,
                Value range: -300 to 10000. 
                Unit: degC.  
                If the value is 2147483647(0x7FFFFFFF), it indicates that the value is invalid."
            ::= { hwInverterEntry 24 }

        hwInverterOperStatus OBJECT-TYPE
            SYNTAX INTEGER
                {
                normal(1),
                alarm(2),
                alarmResume(254),
                unknow(255)
                }
            MAX-ACCESS read-only
            STATUS current
            DESCRIPTION
                "State of the Inverter. It is an enumeration type: 
                If the enumeration value is 1, it indicates that the Inverter is in the normal state;
                If the enumeration value is 2, it indicates that the Inverter is in the alarm state;  
                If the enumeration value is 254, it indicates that the Inverter is in the resume state;   
                If the enumeration value is 255, it indicates Inverter operation status unknown. "
            ::= { hwInverterEntry 99 }

        hwInverterRowStatus OBJECT-TYPE
            SYNTAX RowStatus
            MAX-ACCESS read-only
            STATUS current
            DESCRIPTION
                "RowStatus of Inverter table."
            ::= { hwInverterEntry 100 }

        hwSiteCoolingDevices OBJECT IDENTIFIER ::= { hwSiteMonitorMIBObjects 10 }

        hwCoolingDevicesGroup OBJECT IDENTIFIER ::= { hwSiteCoolingDevices 1 }

        hwCoolingDevicesEquipId OBJECT-TYPE
            SYNTAX Integer32 (19001..19255)
            MAX-ACCESS read-only
            STATUS current
            DESCRIPTION
                "CoolingDevices unit group ID. Value range: 019'001 to 019'255, in which the first digits indicate the device type and the last three digits indicate the device SN. "
            ::= { hwCoolingDevicesGroup 1 }

        hwCoolingDevicesEquipName OBJECT-TYPE
            SYNTAX OCTET STRING (SIZE (0..63))
            MAX-ACCESS read-write
            STATUS current
            DESCRIPTION
                "CoolingDevices unit group name, of the character string type, can be configured by users.
                Otherwise, the configured character can not be any other languages except English."
            ::= { hwCoolingDevicesGroup 2 }

        hwCoolingDevicesMode OBJECT-TYPE
            SYNTAX INTEGER
                {
                fanOnly(1),
                acOnly(2),
                smartMode(3),
                unknown(255)
                }
            MAX-ACCESS read-write
            STATUS current
            DESCRIPTION
                "State of the CoolingDevices TC mode. It is an enumeration type: 
                If the enumeration value is 1, it indicates that the CoolingDeviecs is in fanOnly state;
                If the enumeration value is 2, it indicates that the CoolingDeviecs is in acOnly state;
                If the enumeration value is 3, it indicates that the CoolingDeviecs is in smartMode state;
                If the enumeration value is 255, it indicates Inverter operation status unknown. "
            ::= { hwCoolingDevicesGroup 3 }

        hwCoolingDevicesHighTempAlarmTreshold OBJECT-TYPE
            SYNTAX Integer32 (25..80)
            MAX-ACCESS read-write
            STATUS current
            DESCRIPTION
                "CoolingDevices high temp alarm tres, 
                Value range: 25 to 80 
                Unit: degC.
                and the value is an integer (1). 
                If the value is 2147483647(0x7FFFFFFF), it indicates that the value is invalid."
            ::= { hwCoolingDevicesGroup 4 }

        hwCoolingDevicesHighTempAlarmClearTreshold OBJECT-TYPE
            SYNTAX Integer32 (25..80)
            MAX-ACCESS read-write
            STATUS current
            DESCRIPTION
                "CoolingDevices high temp alarm clear tres, 
                Value range: 25 to 80 
                Unit: degC.
                and the value is an integer (1).  
                If the value is 2147483647(0x7FFFFFFF), it indicates that the value is invalid."
            ::= { hwCoolingDevicesGroup 5 }

        hwCoolingDevicesExpelHidry OBJECT-TYPE
            SYNTAX INTEGER
                {
                no(1),
                yes(2)
                }
            MAX-ACCESS read-write
            STATUS current
            DESCRIPTION
                "State of the CoolingDevices expel hidry. It is an enumeration type: 
                If the enumeration value is 1, it indicates that the CoolingDeviecs is in no state;
                If the enumeration value is 2, it indicates that the CoolingDeviecs is in yes state;
                "
            ::= { hwCoolingDevicesGroup 6 }

        hwCoolingDevicesEquip OBJECT IDENTIFIER ::= { hwSiteCoolingDevices 2 }

        hwFanTable OBJECT-TYPE
            SYNTAX SEQUENCE OF HwFanEntry
            MAX-ACCESS not-accessible
             STATUS current
             DESCRIPTION
                "/"
            ::= { hwCoolingDevicesEquip 1 }

        hwFanEntry OBJECT-TYPE
                        SYNTAX HwFanEntry
            MAX-ACCESS not-accessible
             STATUS current
             DESCRIPTION
                "/"
            INDEX { hwFanIndex }
            ::= { hwFanTable 1 }

        HwFanEntry            ::= SEQUENCE {
                hwFanIndex
                    Unsigned32,
                hwFanEquipId
                    Unsigned32,
                hwFanEquipName
                    OCTET STRING,
                hwFanCtrlMode
                    INTEGER,
                hwFan1Status
                    INTEGER,
                hwFan2Status
                    INTEGER,
                hwFan3Status
                    INTEGER,
                hwFan4Status
                    INTEGER,
                hwFan1Speed
                    Integer32,
                hwFan2Speed
                    Integer32,
                hwFan3Speed
                    Integer32,
                hwFan4Speed
                    Integer32,
                hwFanOperStatus
                    INTEGER,
                hwFanRowStatus
                    RowStatus
            }

        hwFanIndex OBJECT-TYPE
            SYNTAX Unsigned32 (1..256)
            MAX-ACCESS read-only
            STATUS current
            DESCRIPTION
                "Fan table index,which 
                value range: 1 to 256.
                Lines of the device list are restricted by the quantity of Fan."
            ::= { hwFanEntry 1 }

        hwFanEquipId OBJECT-TYPE
            SYNTAX Unsigned32 (20001..20255)
            MAX-ACCESS read-only
            STATUS current
            DESCRIPTION
                "Fan device ID. Value range: 020'001 to 020'255, in which the first digits indicate the device type and the last three digits indicate the device SN. "
            ::= { hwFanEntry 2 }

        hwFanEquipName OBJECT-TYPE
            SYNTAX OCTET STRING (SIZE (0..63))
            MAX-ACCESS read-only
            STATUS current
            DESCRIPTION
                "Fan name, of the character string type, is used to specify Fans. Users can configure it.
                Otherwise, the configured character can not be any other languages except English. "
            ::= { hwFanEntry 3 }

        hwFanCtrlMode OBJECT-TYPE
            SYNTAX INTEGER
                {
                autoControl(1),
                manualControl(2),
                other(3)
                }
            MAX-ACCESS read-write
            STATUS current
            DESCRIPTION
                "State of the Fan ctrl mode. It is an enumeration type: 
                If the enumeration value is 1, it indicates that the fan is in autoControl state;
                If the enumeration value is 2, it indicates that the fan is in manualControl state;
                If the enumeration value is 3, it indicates that the fan is in other state;"
            ::= { hwFanEntry 4 }

        hwFan1Status OBJECT-TYPE
            SYNTAX INTEGER
                {
                normal(1),
                fault(2),
                inexistent(3),
                unknown(255)
                }
            MAX-ACCESS read-only
            STATUS current
            DESCRIPTION
                "State of the Fan1 status. It is an enumeration type: 
                If the enumeration value is 1, it indicates that the fan is in normal state;
                If the enumeration value is 2, it indicates that the fan is in fault state;
                If the enumeration value is 3, it indicates that the fan is in inexistent state;
                If the enumeration value is 255, it indicates that the fan is in unknown state;"
            ::= { hwFanEntry 5 }

        hwFan2Status OBJECT-TYPE
            SYNTAX INTEGER
                {
                normal(1),
                fault(2),
                inexistent(3),
                unknown(255)
                }
            MAX-ACCESS read-only
            STATUS current
            DESCRIPTION
                "State of the Fan2 status. It is an enumeration type: 
                If the enumeration value is 1, it indicates that the fan is in normal state;
                If the enumeration value is 2, it indicates that the fan is in fault state;
                If the enumeration value is 3, it indicates that the fan is in inexistent state;
                If the enumeration value is 255, it indicates that the fan is in unknown state;"
            ::= { hwFanEntry 6 }

        hwFan3Status OBJECT-TYPE
            SYNTAX INTEGER
                {
                normal(1),
                fault(2),
                inexistent(3),
                unknown(255)
                }
            MAX-ACCESS read-only
            STATUS current
            DESCRIPTION
                "State of the Fan3 status. It is an enumeration type: 
                If the enumeration value is 1, it indicates that the fan is in normal state;
                If the enumeration value is 2, it indicates that the fan is in fault state;
                If the enumeration value is 3, it indicates that the fan is in inexistent state;
                If the enumeration value is 255, it indicates that the fan is in unknown state;"
            ::= { hwFanEntry 7 }

        hwFan4Status OBJECT-TYPE
            SYNTAX INTEGER
                {
                normal(1),
                fault(2),
                inexistent(3),
                unknown(255)
                }
            MAX-ACCESS read-only
            STATUS current
            DESCRIPTION
                "State of the Fan4 status. It is an enumeration type: 
                If the enumeration value is 1, it indicates that the fan is in normal state;
                If the enumeration value is 2, it indicates that the fan is in fault state;
                If the enumeration value is 3, it indicates that the fan is in inexistent state;
                If the enumeration value is 255, it indicates that the fan is in unknown state;"
            ::= { hwFanEntry 8 }

        hwFan1Speed OBJECT-TYPE
            SYNTAX Integer32 (0..10000)
            MAX-ACCESS read-only
            STATUS current
            DESCRIPTION
                "Fan1 speed, 
                Value range: 0 to 10000.
                Unit: rpm.
                the value is an integer (1). 
                If the value is 2147483647(0x7FFFFFFF), it indicates that the value is invalid."
            ::= { hwFanEntry 9 }

        hwFan2Speed OBJECT-TYPE
            SYNTAX Integer32 (0..10000)
            MAX-ACCESS read-only
            STATUS current
            DESCRIPTION
                "Fan2 speed, 
                Value range: 0 to 10000.
                Unit: rpm.
                the value is an integer (1). 
                If the value is 2147483647(0x7FFFFFFF), it indicates that the value is invalid."
            ::= { hwFanEntry 10 }

        hwFan3Speed OBJECT-TYPE
            SYNTAX Integer32 (0..10000)
            MAX-ACCESS read-only
            STATUS current
            DESCRIPTION
                "Fan3 speed, 
                Value range: 0 to 10000.
                Unit: rpm.
                the value is an integer (1).
                 If the value is 2147483647(0x7FFFFFFF), it indicates that the value is invalid."
            ::= { hwFanEntry 11 }

        hwFan4Speed OBJECT-TYPE
            SYNTAX Integer32 (0..10000)
            MAX-ACCESS read-only
            STATUS current
            DESCRIPTION
                "Fan4 speed, 
                Value range: 0 to 10000.
                Unit: rpm.
                the value is an integer (1).
                If the value is 2147483647(0x7FFFFFFF), it indicates that the value is invalid."
            ::= { hwFanEntry 12 }

        hwFanOperStatus OBJECT-TYPE
            SYNTAX INTEGER
                {
                normal(1),
                fault(2),
                alarmResume(254),
                unknow(255)
                }
            MAX-ACCESS read-only
            STATUS current
            DESCRIPTION
                "State of the fan. It is an enumeration type: 
                If the enumeration value is 1, it indicates that the Inverter is in the normal state;
                If the enumeration value is 2, it indicates that the Inverter is in the fault state;  
                If the enumeration value is 254, it indicates that the Inverter is in the resume state;   
                If the enumeration value is 255, it indicates Inverter operation status unknown. "
            ::= { hwFanEntry 99 }

        hwFanRowStatus OBJECT-TYPE
            SYNTAX RowStatus
            MAX-ACCESS read-create
            STATUS current
            DESCRIPTION
                "RowStatus fo fan table."
            ::= { hwFanEntry 100 }

        hwDcAirConditionTable OBJECT-TYPE
            SYNTAX SEQUENCE OF HwDcAirConditionEntry
            MAX-ACCESS not-accessible
             STATUS current
             DESCRIPTION
                ""
            ::= { hwCoolingDevicesEquip 2 }

        hwDcAirConditionEntry OBJECT-TYPE
                        SYNTAX HwDcAirConditionEntry
            MAX-ACCESS not-accessible
             STATUS current
             DESCRIPTION
                ""
            INDEX { hwDcAirIndex }
            ::= { hwDcAirConditionTable 1 }

        HwDcAirConditionEntry            ::= SEQUENCE {
                hwDcAirIndex
                    Unsigned32,
                hwDcAirEquipId
                    Unsigned32,
                hwDcAirEquipName
                    OCTET STRING,
                hwDcAirCtrlMode
                    INTEGER,
                hwDcAirCtrlOnOff
                    INTEGER,
                hwDcAirRunStatus
                    INTEGER,
                hwDcAirCompressorRunStatus
                    INTEGER,
                hwDcAirInnrFanSpeed
                    Integer32,
                hwDcAirOuterFanSpeed
                    Integer32,
                hwDcAirCompressorRunTime
                    Integer32,
                hwDcAirRunTime
                    Integer32,
                hwDcAirEnterChannelTemp
                    Integer32,
                hwDcAirPowerOnTempPoint
                    Integer32,
                hwDcAirPowerOffTempPoint
                    Integer32,
                hwAcOffEnergySaving
                    INTEGER,
                hwDcAirPowerOnAcOffPoint
                    Integer32,
                hwDcAirPowerOffAcOffPoint
                    Integer32,
                hwDcAirEquipAddress
                    Unsigned32,
                hwDcAirOperStatus
                    INTEGER,
                hwDcAirRowStatus
                    RowStatus
            }

        hwDcAirIndex OBJECT-TYPE
            SYNTAX Unsigned32
            MAX-ACCESS read-only
            STATUS current
            DESCRIPTION
                "Dc aircondition table index"
            ::= { hwDcAirConditionEntry 1 }

        hwDcAirEquipId OBJECT-TYPE
            SYNTAX Unsigned32
            MAX-ACCESS read-only
            STATUS current
            DESCRIPTION
                "Dc aircondition device ID. "
            ::= { hwDcAirConditionEntry 2 }

        hwDcAirEquipName OBJECT-TYPE
            SYNTAX OCTET STRING (SIZE (0..63))
            MAX-ACCESS read-only
            STATUS current
            DESCRIPTION
                "Dc aircondition name, of the character string type, is used to specify Fans. Users can configure it.
                Otherwise, the configured character can not be any other languages except English. "
            ::= { hwDcAirConditionEntry 3 }

        hwDcAirCtrlMode OBJECT-TYPE
            SYNTAX INTEGER
                {
                autoControl(1),
                manualControl(2),
                unknown(255)
                }
            MAX-ACCESS read-write
            STATUS current
            DESCRIPTION
                "State of the Dc aircondition ctrl mode. It is an enumeration type: 
                If the enumeration value is 1, it indicates that the Dc aircondition is in autoControl state;
                If the enumeration value is 2, it indicates that the Dc aircondition is in manualControl state;
                If the enumeration value is 255, it indicates that the Dc aircondition is in unknown state;"
            ::= { hwDcAirConditionEntry 4 }

        hwDcAirCtrlOnOff OBJECT-TYPE
            SYNTAX INTEGER
                {
                on(1),
                off(2)
                }
            MAX-ACCESS read-write
            STATUS current
            DESCRIPTION
                "State of the Dc aircondition control on or off. It is an enumeration type: 
                If the enumeration value is 1, it indicates that the Dc aircondition is in on state;
                If the enumeration value is 2, it indicates that the Dc aircondition is in off state;"
            ::= { hwDcAirConditionEntry 5 }

        hwDcAirRunStatus OBJECT-TYPE
            SYNTAX INTEGER
                {
                standby(1),
                run(2),
                fault(3),
                unknown(255)
                }
            MAX-ACCESS read-only
            STATUS current
            DESCRIPTION
                "State of the Dc aircondition run status. It is an enumeration type: 
                If the enumeration value is 1, it indicates that the Dc aircondition is in standby state;
                If the enumeration value is 2, it indicates that the Dc aircondition is in run state;
                If the enumeration value is 3, it indicates that the Dc aircondition is in fault state;
                If the enumeration value is 255, it indicates that the Dc aircondition is other state."
            ::= { hwDcAirConditionEntry 6 }

        hwDcAirCompressorRunStatus OBJECT-TYPE
            SYNTAX INTEGER
                {
                standby(1),
                run(2),
                fault(3),
                unknown(255)
                }
            MAX-ACCESS read-only
            STATUS current
            DESCRIPTION
                "State of the Dc air compressor run status. It is an enumeration type: 
                If the enumeration value is 1, it indicates that the Dc aircondition is in standby state;
                If the enumeration value is 2, it indicates that the Dc aircondition is in run state;
                If the enumeration value is 3, it indicates that the Dc aircondition is in fault state;
                If the enumeration value is 255, it indicates that the Dc aircondition is unknown state."
            ::= { hwDcAirConditionEntry 7 }

        hwDcAirInnrFanSpeed OBJECT-TYPE
            SYNTAX Integer32 (0..60000)
            MAX-ACCESS read-only
            STATUS current
            DESCRIPTION
                "Dc aircondition innr speed, 
                Value range: 0 to 60000.
                Unit: rpm,
                and the value is an integer (1).
                If the value is 2147483647(0x7FFFFFFF), it indicates that the value is invalid."
            ::= { hwDcAirConditionEntry 8 }

        hwDcAirOuterFanSpeed OBJECT-TYPE
            SYNTAX Integer32 (0..60000)
            MAX-ACCESS read-only
            STATUS current
            DESCRIPTION
                "Dc aircondition outer speed, 
                Value range: 0.0 to 60000.0.
                Unit: rpm,
                and the value is an integer (1).
                If the value is 2147483647(0x7FFFFFFF), it indicates that the value is invalid."
            ::= { hwDcAirConditionEntry 9 }

        hwDcAirCompressorRunTime OBJECT-TYPE
            SYNTAX Integer32 (0..175200)
            MAX-ACCESS read-only
            STATUS current
            DESCRIPTION
                "Dc aircondition compressor run time, 
                Value range: 0 to 175200.
                Unit: h,
                the value is an integer (1). 
                If the value is 2147483647(0x7FFFFFFF), it indicates that the value is invalid."
            ::= { hwDcAirConditionEntry 10 }

        hwDcAirRunTime OBJECT-TYPE
            SYNTAX Integer32 (0..175200)
            MAX-ACCESS read-only
            STATUS current
            DESCRIPTION
                "Dc aircondition run time, 
                Value range: 0 to 175200.
                Unit: H,
                the value is an integer (1). 
                If the value is 2147483647(0x7FFFFFFF), it indicates that the value is invalid."
            ::= { hwDcAirConditionEntry 11 }

        hwDcAirEnterChannelTemp OBJECT-TYPE
            SYNTAX Integer32 ( -500..1000)
            MAX-ACCESS read-only
            STATUS current
            DESCRIPTION
                "Dc aircondition enter channel temperature, 
                Value range:-500.0 to 1000.0.
                Unit: degC.
                and the value is an integer (1).   
                If the value is 2147483647(0x7FFFFFFF), it indicates that the value is invalid."
            ::= { hwDcAirConditionEntry 13 }

        hwDcAirPowerOnTempPoint OBJECT-TYPE
            SYNTAX Integer32 ( -200..800)
            MAX-ACCESS read-write
            STATUS current
            DESCRIPTION
                "Dc aircondition power on temperature point,
                Value range:-200 to 800.
                Unit: degC.
                the value is an integer (1).  
                If the value is 2147483647(0x7FFFFFFF), it indicates that the value is invalid."
            ::= { hwDcAirConditionEntry 14 }

        hwDcAirPowerOffTempPoint OBJECT-TYPE
            SYNTAX Integer32 ( -200..800)
            MAX-ACCESS read-write
            STATUS current
            DESCRIPTION
                "Dc aircondition power off temperature point, 
                Value range:-200 to 800 
                Unit: degC.
                the value is an integer (1).  
                If the value is 2147483647(0x7FFFFFFF), it indicates that the value is invalid."
            ::= { hwDcAirConditionEntry 15 }

        hwAcOffEnergySaving OBJECT-TYPE
            SYNTAX INTEGER
                {
                disable(1),
                enable(2)
                }
            MAX-ACCESS read-write
            STATUS current
            DESCRIPTION
                "State of the Dc air energy saving status. It is an enumeration type: 
                If the enumeration value is 1, it indicates that the Dc aircondition is in disable state;
                If the enumeration value is 2, it indicates that the Dc aircondition is in enable state;"
            ::= { hwDcAirConditionEntry 17 }

        hwDcAirPowerOnAcOffPoint OBJECT-TYPE
            SYNTAX Integer32 ( -200..800)
            MAX-ACCESS read-write
            STATUS current
            DESCRIPTION
                "Dc aircondition power on ac fail temperature point, 
                Value range:-200 to 800.
                Unit: degC.
                and the value is an integer (1). 
                If the value is 2147483647(0x7FFFFFFF), it indicates that the value is invalid."
            ::= { hwDcAirConditionEntry 18 }

        hwDcAirPowerOffAcOffPoint OBJECT-TYPE
            SYNTAX Integer32 ( -200..800)
            MAX-ACCESS read-write
            STATUS current
            DESCRIPTION
                "Dc aircondition compressor start temperature point, 
                Value range:-200 to 800.
                Unit: degC.
                and the value is an integer (1). 
                If the value is 2147483647(0x7FFFFFFF), it indicates that the value is invalid."
            ::= { hwDcAirConditionEntry 19 }

        hwDcAirEquipAddress OBJECT-TYPE
            SYNTAX Unsigned32 (0..255)
            MAX-ACCESS read-only
            STATUS current
            DESCRIPTION
                " DC Air Device address
                And the value is an integer (1)."
            ::= { hwDcAirConditionEntry 21 }

        hwDcAirOperStatus OBJECT-TYPE
            SYNTAX INTEGER
                {
                standby(1),
                run(2),
                fault(3),
                alarmResume(254),
                unknown(255)
                }
            MAX-ACCESS read-only
            STATUS current
            DESCRIPTION
                "State of the dc aircondition. It is an enumeration type: 
                If the enumeration value is 1, it indicates that the Inverter is in the standby state;
                If the enumeration value is 2, it indicates that the Inverter is in the run state;  
                If the enumeration value is 3, it indicates that the Inverter is in the fault state;
                If the enumeration value is 254, it indicates that the Inverter is in the resume state;     
                If the enumeration value is 255, it indicates Inverter operation status unknown. "
            ::= { hwDcAirConditionEntry 99 }

        hwDcAirRowStatus OBJECT-TYPE
            SYNTAX RowStatus
            MAX-ACCESS read-create
            STATUS current
            DESCRIPTION
                "RowStatus fo dc aircondition table."
            ::= { hwDcAirConditionEntry 100 }

        hwSiteAcAmmeters OBJECT IDENTIFIER ::= { hwSiteMonitorMIBObjects 11 }

        hwSiteAcAmmeterEquip OBJECT IDENTIFIER ::= { hwSiteAcAmmeters 2 }

        hwSiteAcAmmeterTable OBJECT-TYPE
            SYNTAX SEQUENCE OF HwSiteAcAmmeterEntry
            MAX-ACCESS not-accessible
             STATUS current
             DESCRIPTION
                "/"
            ::= { hwSiteAcAmmeterEquip 1 }

        hwSiteAcAmmeterEntry OBJECT-TYPE
                        SYNTAX HwSiteAcAmmeterEntry
            MAX-ACCESS not-accessible
             STATUS current
             DESCRIPTION
                "/"
            INDEX { hwAcAmmeterIndex }
            ::= { hwSiteAcAmmeterTable 1 }

        HwSiteAcAmmeterEntry            ::= SEQUENCE {
                hwAcAmmeterIndex
                    Unsigned32,
                hwAcAmmeterEquipId
                    Unsigned32,
                hwAcAmmeterEquipName
                    OCTET STRING,
                hwAcAmmeterFrequency
                    Unsigned32,
                hwAcAmmeterPhaseL1Voltage
                    Unsigned32,
                hwAcAmmeterPhaseL2Voltage
                    Unsigned32,
                hwAcAmmeterPhaseL3Voltage
                    Unsigned32,
                hwAcAmmeterSetChannelNum
                    Unsigned32,
                hwAcAmmeterClear
                    INTEGER,
                hwAcAmmeterType
                    Unsigned32,
                hwAcAmmeterVersion
                    OCTET STRING,
                hwAcAmmeterPhaseL1CurrentCH1
                    Unsigned32,
                hwAcAmmeterPhaseL2CurrentCH1
                    Unsigned32,
                hwAcAmmeterPhaseL3CurrentCH1
                    Unsigned32,
                hwAcAmmeterTotalActivePowerCH1
                    Integer32,
                hwAcAmmeterTotalPowerFactorCH1
                    Integer32,
                hwAcAmmeterTotalActiveEngryAccCH1
                    Unsigned32,
                hwAcAmmeterPhaseL1CurrentCH2
                    Unsigned32,
                hwAcAmmeterPhaseL2CurrentCH2
                    Unsigned32,
                hwAcAmmeterPhaseL3CurrentCH2
                    Unsigned32,
                hwAcAmmeterTotalActivePowerCH2
                    Integer32,
                hwAcAmmeterTotalPowerFactorCH2
                    Integer32,
                hwAcAmmeterTotalActiveEngryAccCH2
                    Unsigned32,
                hwAcAmmeterPhaseL1CurrentCH3
                    Unsigned32,
                hwAcAmmeterPhaseL2CurrentCH3
                    Unsigned32,
                hwAcAmmeterPhaseL3CurrentCH3
                    Unsigned32,
                hwAcAmmeterTotalActivePowerCH3
                    Integer32,
                hwAcAmmeterTotalPowerFactorCH3
                    Integer32,
                hwAcAmmeterTotalActiveEngryAccCH3
                    Unsigned32,
                hwAcAmmeterPhaseL1CurrentCH4
                    Unsigned32,
                hwAcAmmeterPhaseL2CurrentCH4
                    Unsigned32,
                hwAcAmmeterPhaseL3CurrentCH4
                    Unsigned32,
                hwAcAmmeterTotalActivePowerCH4
                    Integer32,
                hwAcAmmeterTotalPowerFactorCH4
                    Integer32,
                hwAcAmmeterTotalActiveEngryAccCH4
                    Unsigned32,
                hwAcAmmeterPhaseL1ActivePowerCH1
                    Integer32,
                hwAcAmmeterPhaseL2ActivePowerCH1
                    Integer32,
                hwAcAmmeterPhaseL3ActivePowerCH1
                    Integer32,
                hwAcAmmeterPhaseL1ReactivePowerCH1
                    Integer32,
                hwAcAmmeterPhaseL2ReactivePowerCH1
                    Integer32,
                hwAcAmmeterPhaseL3ReactivePowerCH1
                    Integer32,
                hwAcAmmeterPhaseL1PowerFactorCH1
                    Integer32,
                hwAcAmmeterPhaseL2PowerFactorCH1
                    Integer32,
                hwAcAmmeterPhaseL3PowerFactorCH1
                    Integer32,
                hwAcAmmeterTotalReactivePowerCH1
                    Integer32,
                hwAcAmmeterOperStatus
                    INTEGER,
                hwAcAmmeterRowStatus
                    RowStatus
            }

        hwAcAmmeterIndex OBJECT-TYPE
            SYNTAX Unsigned32 (4096..20479)
            MAX-ACCESS read-only
            STATUS current
            DESCRIPTION
                "Ac Ammeter table index,which value range:4096 to 20479. Lines of the device list are restricted by the quantity of AcAmmeter"
            ::= { hwSiteAcAmmeterEntry 1 }

        hwAcAmmeterEquipId OBJECT-TYPE
            SYNTAX Unsigned32 (22001..22255)
            MAX-ACCESS read-only
            STATUS current
            DESCRIPTION
                "Ac Ammeter device ID. Value range: 022'001 to 022'255, in which the first digits indicate the device type and the last three digits indicate the device SN."
            ::= { hwSiteAcAmmeterEntry 2 }

        hwAcAmmeterEquipName OBJECT-TYPE
            SYNTAX OCTET STRING (SIZE (0..63))
            MAX-ACCESS read-only
            STATUS current
            DESCRIPTION
                "Ac Ammeter name, of the character string type, is used to specify Fans. Users can configure it.
                Otherwise, the configured character can not be any other languages except English.
                "
            ::= { hwSiteAcAmmeterEntry 3 }

        hwAcAmmeterFrequency OBJECT-TYPE
            SYNTAX Unsigned32 (0..100000)
            MAX-ACCESS read-only
            STATUS current
            DESCRIPTION
                "Ac Ammeter frequency, 
                Value range: 0.00 to 1000.00.
                Unit: Hz.
                and the value is accurate to two decimal space (.01). 
                If the value is 2147483647(0x7FFFFFFF), it indicates that the value is invalid."
            ::= { hwSiteAcAmmeterEntry 4 }

        hwAcAmmeterPhaseL1Voltage OBJECT-TYPE
            SYNTAX Unsigned32 (0..200000)
            MAX-ACCESS read-only
            STATUS current
            DESCRIPTION
                "Ac Ammeter phase a voltage, 
                Value range: 0.00 to 2000.00.
                Unit: V.
                and the value is accurate to two decimal space (.01). 
                If the value is 2147483647(0x7FFFFFFF), it indicates that the value is invalid."
            ::= { hwSiteAcAmmeterEntry 5 }

        hwAcAmmeterPhaseL2Voltage OBJECT-TYPE
            SYNTAX Unsigned32 (0..200000)
            MAX-ACCESS read-only
            STATUS current
            DESCRIPTION
                "Ac Ammeter phase b voltage, 
                Value range: 0.00 to 2000.0.
                Unit: V.
                and the value is accurate to two decimal space (.01).
                If the value is 2147483647(0x7FFFFFFF), it indicates that the value is invalid."
            ::= { hwSiteAcAmmeterEntry 6 }

        hwAcAmmeterPhaseL3Voltage OBJECT-TYPE
            SYNTAX Unsigned32 (0..200000)
            MAX-ACCESS read-only
            STATUS current
            DESCRIPTION
                "Ac Ammeter phase c voltage, 
                Value range: 0.00 to 2000.0.
                Unit: V.
                and the value is accurate to two decimal space (.01). 
                If the value is 2147483647(0x7FFFFFFF), it indicates that the value is invalid."
            ::= { hwSiteAcAmmeterEntry 7 }

        hwAcAmmeterSetChannelNum OBJECT-TYPE
            SYNTAX Unsigned32 (1..4)
            MAX-ACCESS read-write
            STATUS current
            DESCRIPTION
                "Ac Ammeter set channel number, 
                Value range: 1 to 4. 
                Unit: NA.
                and the value is an integer (1).
                If the value is 2147483647(0x7FFFFFFF), it indicates that the value is invalid."
            ::= { hwSiteAcAmmeterEntry 8 }

        hwAcAmmeterClear OBJECT-TYPE
            SYNTAX INTEGER
                {
                clear(1)
                }
            MAX-ACCESS read-write
            STATUS current
            DESCRIPTION
                "Ac Ammeter clear communication failure . It is an enumeration type: 
                If the enumeration value is 1, it indicates that the ac ammeter clear communication failure alarm;"
            ::= { hwSiteAcAmmeterEntry 9 }

        hwAcAmmeterType OBJECT-TYPE
            SYNTAX Unsigned32 (0..65535)
            MAX-ACCESS read-only
            STATUS current
            DESCRIPTION
                "Ac Ammeter type, Value range: 0 to 65535. And the value is an integer(1)."
            ::= { hwSiteAcAmmeterEntry 10 }

        hwAcAmmeterVersion OBJECT-TYPE
            SYNTAX OCTET STRING (SIZE (0..56))
            MAX-ACCESS read-only
            STATUS current
            DESCRIPTION
                "Ac Ammeter version, of the character string type, is used to specify Ac Ammeter. Users can not configure it."
            ::= { hwSiteAcAmmeterEntry 11 }

        hwAcAmmeterPhaseL1CurrentCH1 OBJECT-TYPE
            SYNTAX Unsigned32 (0..100000)
            MAX-ACCESS read-only
            STATUS current
            DESCRIPTION
                "Ac Ammeter phase a current of channel 1, 
                Value range: 0.00 to 1000.0.
                Unit: A.
                and the value is accurate to two decimal space (.01). 
                If the value is 2147483647(0x7FFFFFFF), it indicates that the value is invalid."
            ::= { hwSiteAcAmmeterEntry 12 }

        hwAcAmmeterPhaseL2CurrentCH1 OBJECT-TYPE
            SYNTAX Unsigned32 (0..100000)
            MAX-ACCESS read-only
            STATUS current
            DESCRIPTION
                "Ac Ammeter phase b current of channel 1, 
                Value range: 0.00 to 1000.0.
                Unit: A.
                and the value is accurate to two decimal space (.01). 
                If the value is 2147483647(0x7FFFFFFF), it indicates that the value is invalid."
            ::= { hwSiteAcAmmeterEntry 13 }

        hwAcAmmeterPhaseL3CurrentCH1 OBJECT-TYPE
            SYNTAX Unsigned32 (0..100000)
            MAX-ACCESS read-only
            STATUS current
            DESCRIPTION
                "Ac Ammeter phase c current of channel 1, 
                Value range: 0.00 to 1000.0.
                Unit: A.
                and the value is accurate to two decimal space (.01).
                If the value is 2147483647(0x7FFFFFFF), it indicates that the value is invalid."
            ::= { hwSiteAcAmmeterEntry 14 }

        hwAcAmmeterTotalActivePowerCH1 OBJECT-TYPE
            SYNTAX Integer32 (-100000000..100000000)
            MAX-ACCESS read-only
            STATUS current
            DESCRIPTION
                "Ac Ammeter phase c current of channel 1, 
                Value range: -1000000.00 to 1000000.00.
                Unit: kW.
                and the value is accurate to two decimal space (.01). 
                If the value is 2147483647(0x7FFFFFFF), it indicates that the value is invalid."
            ::= { hwSiteAcAmmeterEntry 15 }

        hwAcAmmeterTotalPowerFactorCH1 OBJECT-TYPE
            SYNTAX Integer32 (-1000..1000)
            MAX-ACCESS read-only
            STATUS current
            DESCRIPTION
                "Ac Ammeter total power factor of channel 1, 
                Value range: -10.00 to 10.00.
                and the value is accurate to two decimal space (.01). 
                If the value is 2147483647(0x7FFFFFFF), it indicates that the value is invalid."
            ::= { hwSiteAcAmmeterEntry 16 }

        hwAcAmmeterTotalActiveEngryAccCH1 OBJECT-TYPE
            SYNTAX Unsigned32 (0..10000000000000)
            MAX-ACCESS read-only
            STATUS current
            DESCRIPTION
                "Ac Ammeter total active engry acc of channel 1, 
                Value range: 0.00 to 1000000000.00.
                Unit: kWh.
                and the value is accurate to two decimal space (.01). 
                If the value is 2147483647(0x7FFFFFFF), it indicates that the value is invalid."
            ::= { hwSiteAcAmmeterEntry 17 }

        hwAcAmmeterPhaseL1CurrentCH2 OBJECT-TYPE
            SYNTAX Unsigned32 (0..100000)
            MAX-ACCESS read-only
            STATUS current
            DESCRIPTION
                "Ac Ammeter phase a current of channel 2, 
                Value range: 0.00 to 1000.00.
                Unit: A.
                and the value is accurate to two decimal space (.01).
                If the value is 2147483647(0x7FFFFFFF), it indicates that the value is invalid."
            ::= { hwSiteAcAmmeterEntry 18 }

        hwAcAmmeterPhaseL2CurrentCH2 OBJECT-TYPE
            SYNTAX Unsigned32 (0..100000)
            MAX-ACCESS read-only
            STATUS current
            DESCRIPTION
                "Ac Ammeter phase b current of channel 2, 
                Value range: 0.00 to 1000.00.
                Unit: A.
                and the value is accurate to two decimal space (.01).
                If the value is 2147483647(0x7FFFFFFF), it indicates that the value is invalid."
            ::= { hwSiteAcAmmeterEntry 19 }

        hwAcAmmeterPhaseL3CurrentCH2 OBJECT-TYPE
            SYNTAX Unsigned32 (0..100000)
            MAX-ACCESS read-only
            STATUS current
            DESCRIPTION
                "Ac Ammeter phase c current of channel 2, 
                Value range: 0.00 to 1000.00.
                Unit: A.
                and the value is accurate to two decimal space (.01). 
                If the value is 2147483647(0x7FFFFFFF), it indicates that the value is invalid."
            ::= { hwSiteAcAmmeterEntry 20 }

        hwAcAmmeterTotalActivePowerCH2 OBJECT-TYPE
            SYNTAX Integer32 (-100000000..100000000)
            MAX-ACCESS read-only
            STATUS current
            DESCRIPTION
                "Ac Ammeter phase c current of channel 2, 
                Value range: -1000000.00 to 1000000.00.
                Unit: kW.
                and the value is accurate to two decimal space (.01). 
                If the value is 2147483647(0x7FFFFFFF), it indicates that the value is invalid."
            ::= { hwSiteAcAmmeterEntry 21 }

        hwAcAmmeterTotalPowerFactorCH2 OBJECT-TYPE
            SYNTAX Integer32 (-1000..1000)
            MAX-ACCESS read-only
            STATUS current
            DESCRIPTION
                "Ac Ammeter total power factor of channel 2, 
                Value range: -10.00 to 10.00.
                and the value is accurate to two decimal space (.01). 
                If the value is 2147483647(0x7FFFFFFF), it indicates that the value is invalid."
            ::= { hwSiteAcAmmeterEntry 22 }

        hwAcAmmeterTotalActiveEngryAccCH2 OBJECT-TYPE
            SYNTAX Unsigned32 (0..100000000000)
            MAX-ACCESS read-only
            STATUS current
            DESCRIPTION
                "Ac Ammeter total active engry acc of channel 2, 
                Value range: 0.00 to 1000000000.00.
                Unit: A.
                and the value is accurate to two decimal space (.01). 
                If the value is 2147483647(0x7FFFFFFF), it indicates that the value is invalid."
            ::= { hwSiteAcAmmeterEntry 23 }

        hwAcAmmeterPhaseL1CurrentCH3 OBJECT-TYPE
            SYNTAX Unsigned32 (0..100000)
            MAX-ACCESS read-only
            STATUS current
            DESCRIPTION
                "Ac Ammeter phase a current of channel 3, 
                Value range: 0.00 to 1000.00.
                Unit: A.
                and the value is accurate to two decimal space (.01). 
                If the value is 2147483647(0x7FFFFFFF), it indicates that the value is invalid."
            ::= { hwSiteAcAmmeterEntry 24 }

        hwAcAmmeterPhaseL2CurrentCH3 OBJECT-TYPE
            SYNTAX Unsigned32 (0..100000)
            MAX-ACCESS read-only
            STATUS current
            DESCRIPTION
                "Ac Ammeter phase b current of channel 3, 
                Value range: 0.00 to 1000.00.
                Unit: A.
                and the value is accurate to two decimal space (.01). 
                If the value is 2147483647(0x7FFFFFFF), it indicates that the value is invalid."
            ::= { hwSiteAcAmmeterEntry 25 }

        hwAcAmmeterPhaseL3CurrentCH3 OBJECT-TYPE
            SYNTAX Unsigned32 (0..100000)
            MAX-ACCESS read-only
            STATUS current
            DESCRIPTION
                "Ac Ammeter phase c current of channel 3, 
                Value range: 0.00 to 1000.00.
                Unit: A.
                and the value is accurate to two decimal space (.01). 
                If the value is 2147483647(0x7FFFFFFF), it indicates that the value is invalid."
            ::= { hwSiteAcAmmeterEntry 26 }

        hwAcAmmeterTotalActivePowerCH3 OBJECT-TYPE
            SYNTAX Integer32 (-100000000..100000000)
            MAX-ACCESS read-only
            STATUS current
            DESCRIPTION
                "Ac Ammeter phase c current of channel 3, 
                Value range: -1000000.00 to 1000000.00.
                Unit: kW.
                and the value is accurate to two decimal space (.01). 
                If the value is 2147483647(0x7FFFFFFF), it indicates that the value is invalid."
            ::= { hwSiteAcAmmeterEntry 27 }

        hwAcAmmeterTotalPowerFactorCH3 OBJECT-TYPE
            SYNTAX Integer32 (-1000..1000)
            MAX-ACCESS read-only
            STATUS current
            DESCRIPTION
                "Ac Ammeter total power factor of channel 3, 
                Value range: -10.00 to 10.00.
                and the value is accurate to two decimal space (.01).
                If the value is 2147483647(0x7FFFFFFF), it indicates that the value is invalid."
            ::= { hwSiteAcAmmeterEntry 28 }

        hwAcAmmeterTotalActiveEngryAccCH3 OBJECT-TYPE
            SYNTAX Unsigned32 (0..100000000000)
            MAX-ACCESS read-only
            STATUS current
            DESCRIPTION
                "Ac Ammeter total active engry acc of channel 3, 
                Value range: 0.00 to 1000000000.00.
                Unit: kWh.
                and the value is accurate to two decimal space (.01). 
                If the value is 2147483647(0x7FFFFFFF), it indicates that the value is invalid."
            ::= { hwSiteAcAmmeterEntry 29 }

        hwAcAmmeterPhaseL1CurrentCH4 OBJECT-TYPE
            SYNTAX Unsigned32 (0..100000)
            MAX-ACCESS read-only
            STATUS current
            DESCRIPTION
                "Ac Ammeter phase a current of channel 4, 
                Value range: 0 to 1000.
                Unit: A.
                and the value is accurate to two decimal space (.01). 
                If the value is 2147483647(0x7FFFFFFF), it indicates that the value is invalid."
            ::= { hwSiteAcAmmeterEntry 30 }

        hwAcAmmeterPhaseL2CurrentCH4 OBJECT-TYPE
            SYNTAX Unsigned32 (0..100000)
            MAX-ACCESS read-only
            STATUS current
            DESCRIPTION
                "Ac Ammeter phase b current of channel 4, 
                Value range: 0 to 1000.
                Unit: A.
                and the value is accurate to two decimal space (.01). 
                If the value is 2147483647(0x7FFFFFFF), it indicates that the value is invalid."
            ::= { hwSiteAcAmmeterEntry 31 }

        hwAcAmmeterPhaseL3CurrentCH4 OBJECT-TYPE
            SYNTAX Unsigned32 (0..100000)
            MAX-ACCESS read-only
            STATUS current
            DESCRIPTION
                "Ac Ammeter phase c current of channel 4, 
                Value range: 0 to 1000.
                Unit: A.
                and the value is accurate to two decimal space (.01). 
                If the value is 2147483647(0x7FFFFFFF), it indicates that the value is invalid."
            ::= { hwSiteAcAmmeterEntry 32 }

        hwAcAmmeterTotalActivePowerCH4 OBJECT-TYPE
            SYNTAX Integer32 (-100000000..100000000)
            MAX-ACCESS read-only
            STATUS current
            DESCRIPTION
                "Ac Ammeter phase c current of channel 4, 
                Value range: -1000000 to 1000000.
                Unit: kW.
                and the value is accurate to two decimal space (.01). 
                If the value is 2147483647(0x7FFFFFFF), it indicates that the value is invalid."
            ::= { hwSiteAcAmmeterEntry 33 }

        hwAcAmmeterTotalPowerFactorCH4 OBJECT-TYPE
            SYNTAX Integer32 (-1000..1000)
            MAX-ACCESS read-only
            STATUS current
            DESCRIPTION
                "Ac Ammeter total power factor of channel 4, 
                Value range: -10.00 to 10.00.
                and the value is accurate to two decimal space (.01).
                If the value is 2147483647(0x7FFFFFFF), it indicates that the value is invalid."
            ::= { hwSiteAcAmmeterEntry 34 }

        hwAcAmmeterTotalActiveEngryAccCH4 OBJECT-TYPE
            SYNTAX Unsigned32 (0..100000000000)
            MAX-ACCESS read-only
            STATUS current
            DESCRIPTION
                "Ac Ammeter total active engry acc of channel 4, 
                Value range: 0 to 1000000000.
                Unit: kWh.
                and the value is accurate to two decimal space (.01). 
                If the value is 2147483647(0x7FFFFFFF), it indicates that the value is invalid."
            ::= { hwSiteAcAmmeterEntry 35 }

        hwAcAmmeterPhaseL1ActivePowerCH1 OBJECT-TYPE
            SYNTAX Integer32 (-100000000..100000000)
            MAX-ACCESS read-only
            STATUS current
            DESCRIPTION
                "The phase L1 Active Power of channel1; 
                Value range: -1000000.00 to 1000000.00, 
                and the value is accurate to two decimal place (.01).
                units: kW."
            ::= { hwSiteAcAmmeterEntry 36 }

        hwAcAmmeterPhaseL2ActivePowerCH1 OBJECT-TYPE
            SYNTAX Integer32 (-100000000..100000000)
            MAX-ACCESS read-only
            STATUS current
            DESCRIPTION
                "The phase L2 Active Power of channel1; 
                Value range: -1000000.00 to 1000000.00, 
                and the value is accurate to two decimal place (.01).
                units: kW"
            ::= { hwSiteAcAmmeterEntry 37 }

        hwAcAmmeterPhaseL3ActivePowerCH1 OBJECT-TYPE
            SYNTAX Integer32 (-100000000..100000000)
            MAX-ACCESS read-only
            STATUS current
            DESCRIPTION
                "The phase L3 Active Power of channel1; 
                Value range: -1000000.00 to 1000000.00, 
                and the value is accurate to two decimal place (.01).
                units: kW."
            ::= { hwSiteAcAmmeterEntry 38 }

        hwAcAmmeterPhaseL1ReactivePowerCH1 OBJECT-TYPE
            SYNTAX Integer32 (-100000000..100000000)
            MAX-ACCESS read-only
            STATUS current
            DESCRIPTION
                "The phase L1 Reactive Power of channel1; 
                Value range: -1000000.00 to 1000000.00, 
                and the value is accurate to two decimal place (.01).
                units: kvar."
            ::= { hwSiteAcAmmeterEntry 39 }

        hwAcAmmeterPhaseL2ReactivePowerCH1 OBJECT-TYPE
            SYNTAX Integer32 (-100000000..100000000)
            MAX-ACCESS read-only
            STATUS current
            DESCRIPTION
                "The phase L2 Reactive Power of channel1; 
                Value range: -1000000.00 to 1000000.00, 
                and the value is accurate to two decimal place (.01).
                units: kvar."
            ::= { hwSiteAcAmmeterEntry 40 }

        hwAcAmmeterPhaseL3ReactivePowerCH1 OBJECT-TYPE
            SYNTAX Integer32 (-100000000..100000000)
            MAX-ACCESS read-only
            STATUS current
            DESCRIPTION
                "The phase L3 Active Power of channel1; 
                Value range: -1000000.00 to 1000000.00, 
                and the value is accurate to two decimal place (.01).
                units: kvar."
            ::= { hwSiteAcAmmeterEntry 41 }

        hwAcAmmeterPhaseL1PowerFactorCH1 OBJECT-TYPE
            SYNTAX Integer32 (-100..100)
            MAX-ACCESS read-only
            STATUS current
            DESCRIPTION
                "The phase L1 Power Factor of channel1; 
                Value range: -1.00 to 1.00, 
                and the value is accurate to two decimal place (.01).
                units: NA."
            ::= { hwSiteAcAmmeterEntry 42 }

        hwAcAmmeterPhaseL2PowerFactorCH1 OBJECT-TYPE
            SYNTAX Integer32 (-100..100)
            MAX-ACCESS read-only
            STATUS current
            DESCRIPTION
                "The phase L2 Power Factor of channel1; 
                Value range: -1.00 to 1.00, 
                and the value is accurate to two decimal place (.01).
                units: NA."
            ::= { hwSiteAcAmmeterEntry 43 }

        hwAcAmmeterPhaseL3PowerFactorCH1 OBJECT-TYPE
            SYNTAX Integer32 (-100..100)
            MAX-ACCESS read-only
            STATUS current
            DESCRIPTION
                "The phase L3 Power Factor of channel1; 
                Value range: -1.00 to 1.00, 
                and the value is accurate to two decimal place (.01).
                units: NA."
            ::= { hwSiteAcAmmeterEntry 44 }

        hwAcAmmeterTotalReactivePowerCH1 OBJECT-TYPE
            SYNTAX Integer32 (-100000000..100000000)
            MAX-ACCESS read-only
            STATUS current
            DESCRIPTION
                "The Total Reactive Power of channel1; 
                Value range: -1000000.00 to 1000000.00, 
                and the value is accurate to two decimal place (.01).
                units: kvar."
            ::= { hwSiteAcAmmeterEntry 45 }

        hwAcAmmeterOperStatus OBJECT-TYPE
            SYNTAX INTEGER
                {
                normal(1),
                fault(2),
                unknown(255)
                }
            MAX-ACCESS read-only
            STATUS current
            DESCRIPTION
                "State of the Ac Ammeter. It is an enumeration type: 
                If the enumeration value is 1, it indicates that the Ac Ammeter is in the normal state;
                If the enumeration value is 2, it indicates that the Ac Ammeter is in the fault state;  
                If the enumeration value is 255, it indicates that the Ac Ammeter is in the unknown state;  "
            ::= { hwSiteAcAmmeterEntry 99 }

        hwAcAmmeterRowStatus OBJECT-TYPE
            SYNTAX RowStatus
            MAX-ACCESS read-create
            STATUS current
            DESCRIPTION
                "RowStatus fo Ac Ammeter table."
            ::= { hwSiteAcAmmeterEntry 100 }

        hwSiteDG OBJECT IDENTIFIER ::= { hwSiteMonitorMIBObjects 12 }

        hwDGGroup OBJECT IDENTIFIER ::= { hwSiteDG 1 }

        hwDGGroupId OBJECT-TYPE
            SYNTAX Unsigned32
            MAX-ACCESS read-only
            STATUS current
            DESCRIPTION
                "Device group ID of the DG module. It is the unique ID of the DG module group, and its default value: 023,000. 
                The first digits indicate the device type and the last three digits indicate the device SN. 
                If the last three digits are 000, it indicates a virtual device. "
            ::= { hwDGGroup 1 }

        hwDGGroupName OBJECT-TYPE
            SYNTAX OCTET STRING (SIZE (0..56))
            MAX-ACCESS read-only
            STATUS current
            DESCRIPTION
                "Name of the DG module group, character string type, is used to specify the DG module group. Otherwise, the configured character can not be any other languages except English."
            ::= { hwDGGroup 2 }

        hwDGAmount OBJECT-TYPE
            SYNTAX Unsigned32 (0..2)
            MAX-ACCESS read-write
            STATUS current
            DESCRIPTION
                "Total quantity of the DG modules. Value range: 0 to 2. Units:pcs."
            ::= { hwDGGroup 3 }

        hwDG OBJECT IDENTIFIER ::= { hwSiteDG 2 }

        hwDGTable OBJECT-TYPE
            SYNTAX SEQUENCE OF HwDGEntry
            MAX-ACCESS not-accessible
             STATUS current
             DESCRIPTION
                "/"
            ::= { hwDG 1 }

        hwDGEntry OBJECT-TYPE
                        SYNTAX HwDGEntry
            MAX-ACCESS not-accessible
             STATUS current
             DESCRIPTION
                "/"
            INDEX { hwDGIndex }
            ::= { hwDGTable 1 }

        HwDGEntry            ::= SEQUENCE {
                hwDGIndex
                    Integer32,
                hwDGEquipId
                    Unsigned32,
                hwDGEquipName
                    OCTET STRING,
                hwDGType
                    INTEGER,
                hwDGAphaseVoltage
                    Unsigned32,
                hwDGBphaseVoltage
                    Unsigned32,
                hwDGCphaseVoltage
                    Unsigned32,
                hwDGAphaseCurrent
                    Unsigned32,
                hwDGBphaseCurrent
                    Unsigned32,
                hwDGCphaseCurrent
                    Unsigned32,
                hwDGOutputPower
                    Unsigned32,
                hwDGFrequency
                    Unsigned32,
                hwDGBatteryVoltage
                    Unsigned32,
                hwDGTotalRuntime
                    Unsigned32,
                hwDGAphasePowerFactor
                    Integer32,
                hwDGBphasePowerFactor
                    Integer32,
                hwDGCphasePowerFactor
                    Integer32,
                hwDGLoadRate
                    Unsigned32,
                hwDGOnOffControl
                    INTEGER,
                hwDGFaultReset
                    INTEGER,
                hwDGMaintenanceConfirm
                    INTEGER,
                hwDGOperStatus
                    INTEGER,
                hwDGRowStatus
                    RowStatus
            }

        hwDGIndex OBJECT-TYPE
            SYNTAX Integer32 (0..256)
            MAX-ACCESS read-only
            STATUS current
            DESCRIPTION
                "DG table index,which value range:1 to 256. Lines of the device list are restricted by the quantity of DG."
            ::= { hwDGEntry 1 }

        hwDGEquipId OBJECT-TYPE
            SYNTAX Unsigned32 (23001..23255)
            MAX-ACCESS read-only
            STATUS current
            DESCRIPTION
                "DG device ID. Value range: 023'001 to 023'255, in which the first digits indicate the device type and the last three digits indicate the device SN."
            ::= { hwDGEntry 2 }

        hwDGEquipName OBJECT-TYPE
            SYNTAX OCTET STRING (SIZE (0..63))
            MAX-ACCESS read-only
            STATUS current
            DESCRIPTION
                "Device name of the DG module, character string type, is used to specify the DG module. Otherwise, the configured character can not be any other languages except English."
            ::= { hwDGEntry 3 }

        hwDGType OBJECT-TYPE
            SYNTAX INTEGER {
                intelligent(1),
                nonIntelligent(2),
                unknown(255)
            }
            MAX-ACCESS read-only
            STATUS current
            DESCRIPTION
                "Indicates the type of the DG module:
                  - intelligent(1): An intelligent DG module
                  - nonIntelligent(2): A non-intelligent module
                  - unknown(255): An unknown module"
            ::= { hwDGEntry 4 }

        hwDGAphaseVoltage OBJECT-TYPE
            SYNTAX Unsigned32 (0..5000)
            MAX-ACCESS read-only
            STATUS current
            DESCRIPTION
                "A-phase voltage. 
                Value range: 0 to 500, 
                units: V, 
                and the value is accurate to one decimal place (.1)."
            ::= { hwDGEntry 5 }

        hwDGBphaseVoltage OBJECT-TYPE
            SYNTAX Unsigned32 (0..5000)
            MAX-ACCESS read-only
            STATUS current
            DESCRIPTION
                "B-phase voltage. 
                Value range: 0 to 500, 
                units: V, 
                and the value is accurate to one decimal place (.1)."
            ::= { hwDGEntry 6 }

        hwDGCphaseVoltage OBJECT-TYPE
            SYNTAX Unsigned32 (0..5000)
            MAX-ACCESS read-only
            STATUS current
            DESCRIPTION
                "C-phase voltage. 
                Value range: 0 to 500, 
                units: V, 
                and the value is accurate to one decimal place (.1)."
            ::= { hwDGEntry 7 }

        hwDGAphaseCurrent OBJECT-TYPE
            SYNTAX Unsigned32 (0..100)
            MAX-ACCESS read-only
            STATUS current
            DESCRIPTION
                "A-phase current. 
                Value range: 0 to 100, 
                units: A, 
                and the value is  an integer (1)."
            ::= { hwDGEntry 8 }

        hwDGBphaseCurrent OBJECT-TYPE
            SYNTAX Unsigned32 (0..100)
            MAX-ACCESS read-only
            STATUS current
            DESCRIPTION
                "B-phase current. 
                Value range: 0 to 100, 
                units: A, 
                and the value is  an integer (1)."
            ::= { hwDGEntry 9 }

        hwDGCphaseCurrent OBJECT-TYPE
            SYNTAX Unsigned32 (0..100)
            MAX-ACCESS read-only
            STATUS current
            DESCRIPTION
                "C-phase current. 
                Value range: 0 to 100, 
                units: A, 
                and the value is  an integer (1)."
            ::= { hwDGEntry 10 }

        hwDGOutputPower OBJECT-TYPE
            SYNTAX Unsigned32 (0..1000)
            MAX-ACCESS read-only
            STATUS current
            DESCRIPTION
                "DG output power.
                Value range: 0 to 100, 
                units: kw, 
                and the value is one decimal space (.1)."
            ::= { hwDGEntry 11 }

        hwDGFrequency OBJECT-TYPE
            SYNTAX Unsigned32 (50..1200)
            MAX-ACCESS read-only
            STATUS current
            DESCRIPTION
                "The frequency of DG. 
                Value range: 5 to 120, 
                units: Hz, 
                and the value is one decimal space (.1)."
            ::= { hwDGEntry 12 }

        hwDGBatteryVoltage OBJECT-TYPE
            SYNTAX Unsigned32 (0..240)
            MAX-ACCESS read-only
            STATUS current
            DESCRIPTION
                "The voltage of DG battery. 
                Value range: 0 to 24, 
                units: V, 
                and the value is one decimal space (.1)."
            ::= { hwDGEntry 13 }

        hwDGTotalRuntime OBJECT-TYPE
            SYNTAX Unsigned32 (0..8760000)
            MAX-ACCESS read-only
            STATUS current
            DESCRIPTION
                "The total running time of DG, 
                Value range: 0 to 876000,
                units: h, 
                and the value is one decimal space (.1)."
            ::= { hwDGEntry 14 }

        hwDGAphasePowerFactor OBJECT-TYPE
            SYNTAX Integer32 (-100..100)
            MAX-ACCESS read-only
            STATUS current
            DESCRIPTION
                "A phase power factor of DG, 
                Value range: -1 to 1, 
                units: , 
                and the value is two decimal space (.01)."
            ::= { hwDGEntry 15 }

        hwDGBphasePowerFactor OBJECT-TYPE
            SYNTAX Integer32 (-100..100)
            MAX-ACCESS read-only
            STATUS current
            DESCRIPTION
                "B phase power factor of DG, 
                Value range: -1 to 1,
                units: , 
                and the value is two decimal space (.01)."
            ::= { hwDGEntry 16 }

        hwDGCphasePowerFactor OBJECT-TYPE
            SYNTAX Integer32 (-100..100)
            MAX-ACCESS read-only
            STATUS current
            DESCRIPTION
                "C phase power factor of DG, 
                Value range: -1 to 1, 
                units: , 
                and the value is two decimal space (.01)."
            ::= { hwDGEntry 17 }

        hwDGLoadRate OBJECT-TYPE
            SYNTAX Unsigned32 (0..1000)
            MAX-ACCESS read-only
            STATUS current
            DESCRIPTION
                "The load rate of DG, 
                Value range: 0 to 100, 
                units: %, 
                and the value is one decimal space (.1). "
            ::= { hwDGEntry 18 }

        hwDGOnOffControl OBJECT-TYPE
            SYNTAX INTEGER
                {
                on(1),
                off(2),
                unknown(255)
                }
            MAX-ACCESS read-write
            STATUS current
            DESCRIPTION
                "Power-on or power-off of the DG module, is an enumeration value. Users can modify the enumeration value of this node, thus controlling of the power-on or power-off of the DG module:
                  If the NMS notifies the SNMP agent that this node is set to 1, it indicates power-on of the DG module;
                  If the NMS notifies the SNMP agent that this node is set to 2, it indicates power-off of the DG module.
                  If the NMS notifies the SNMP agent that this node is set to 255, it indicates unknown of the DG module."
            ::= { hwDGEntry 19 }

        hwDGFaultReset OBJECT-TYPE
            SYNTAX INTEGER
                {
                reset(1),
                unknown(255)
                }
            MAX-ACCESS read-write
            STATUS current
            DESCRIPTION
                "DG fault reset."
            ::= { hwDGEntry 20 }

        hwDGMaintenanceConfirm OBJECT-TYPE
            SYNTAX INTEGER
                {
                reset(1),
                unknown(255)
                }
            MAX-ACCESS read-write
            STATUS current
            DESCRIPTION
                "DG maintenance confirm."
            ::= { hwDGEntry 21 }

        hwDGOperStatus OBJECT-TYPE
            SYNTAX INTEGER
                {
                stop(1),
                running(2),
                unknown(255)
                }
            MAX-ACCESS read-only
            STATUS current
            DESCRIPTION
                "State of the DG. It is an enumeration type: 
                If the enumeration value is 1, it indicates that the DG is in the normal state;
                If the enumeration value is 2, it indicates that the DG is in the fault state;  
                If the enumeration value is 255, it indicates that the DG is in the unknown state;  "
            ::= { hwDGEntry 99 }

        hwDGRowStatus OBJECT-TYPE
            SYNTAX RowStatus
            MAX-ACCESS read-create
            STATUS current
            DESCRIPTION
                "RowStatus fo DG."
            ::= { hwDGEntry 100 }

        hwSiteSSU OBJECT IDENTIFIER ::= { hwSiteMonitorMIBObjects 13 }

        hwSSUGroup OBJECT IDENTIFIER ::= { hwSiteSSU 1 }

        hwSSUGroupId OBJECT-TYPE
            SYNTAX Unsigned32
            MAX-ACCESS read-only
            STATUS current
            DESCRIPTION
                "Device group ID of the SSU module. It is the unique ID of the SSU module group, and its default value: 024,000. 
                The first digits indicate the device type and the last three digits indicate the device SN. If the last three digits are 000, it indicates a virtual device. "
            ::= { hwSSUGroup 1 }

        hwSSUGroupName OBJECT-TYPE
            SYNTAX OCTET STRING (SIZE (0..56))
            MAX-ACCESS read-only
            STATUS current
            DESCRIPTION
                "Name of the SSU module group, character string type, is used to specify the SSU module group. 
                Otherwise, the configured character can not be any other languages except English."
            ::= { hwSSUGroup 2 }

        hwSSUTotalCurrent OBJECT-TYPE
            SYNTAX Unsigned32 (0..10000)
            MAX-ACCESS read-only
            STATUS current
            DESCRIPTION
                "The total output current of SSU. 
                Value range: 0 to 1000, 
                units: A, 
                and the value is one decimal space (.1)."
            ::= { hwSSUGroup 3 }

        hwSSUTotalOutputPowerConsumption OBJECT-TYPE
            SYNTAX Unsigned32 (0..100000000)
            MAX-ACCESS read-only
            STATUS current
            DESCRIPTION
                "The total output current of SSU. 
                Value range: 0 to 10000000, 
                units: kWh, 
                and the value is one decimal space (.1)."
            ::= { hwSSUGroup 4 }

        hwSSUClearLostAlarms OBJECT-TYPE
            SYNTAX INTEGER
                {
                normal(1), 
                clear(2),
                unknown(255)
                }
            MAX-ACCESS read-write
            STATUS current
            DESCRIPTION
                "Clear the lost alarm of SSU."
            ::= { hwSSUGroup 5 }

        hwSSUAmount OBJECT-TYPE
            SYNTAX Unsigned32 (0..100)
            MAX-ACCESS read-only
            STATUS current
            DESCRIPTION
                "Total quantity of the SSU modules. Value range: 0 to 100. Units:pcs."
            ::= { hwSSUGroup 6 }

        hwSSUTotalOutputPower OBJECT-TYPE
            SYNTAX Unsigned32 (0..100000000)
            MAX-ACCESS read-only
            STATUS current
            DESCRIPTION
                "resolution: 0.1kw"
            ::= { hwSSUGroup 7 }

        hwSSUFaultNumber OBJECT-TYPE
            SYNTAX Unsigned32 (0..100)
            MAX-ACCESS read-only
            STATUS current
            DESCRIPTION
                "number of fault solar modules "
            ::= { hwSSUGroup 8 }

        hwSSU OBJECT IDENTIFIER ::= { hwSiteSSU 2 }

        hwSSUTable OBJECT-TYPE
            SYNTAX SEQUENCE OF HwSSUEntry
            MAX-ACCESS not-accessible
             STATUS current
             DESCRIPTION
                "/"
            ::= { hwSSU 1 }

        hwSSUEntry OBJECT-TYPE
                        SYNTAX HwSSUEntry
            MAX-ACCESS not-accessible
             STATUS current
             DESCRIPTION
                "/"
            INDEX { hwSSUIndex }
            ::= { hwSSUTable 1 }

        HwSSUEntry            ::= SEQUENCE {
                hwSSUIndex
                    Integer32,
                hwSSUEquipId
                    Unsigned32,
                hwSSUEquipName
                    OCTET STRING,
                hwSSURunningState
                    INTEGER,
                hwSSUInputVoltage
                    Unsigned32,
                hwSSUOutputVoltage
                    Unsigned32,
                hwSSUOutputCurrent
                    Unsigned32,
                hwSSUAddress
                    Unsigned32,
                hwSSURowStatus
                    RowStatus
            }

        hwSSUIndex OBJECT-TYPE
            SYNTAX Integer32 (0..256)
            MAX-ACCESS read-only
            STATUS current
            DESCRIPTION
                "SSU table index,which value range:1 to 256. Lines of the device list are restricted by the quantity of SSU."
            ::= { hwSSUEntry 1 }

        hwSSUEquipId OBJECT-TYPE
            SYNTAX Unsigned32 (24001..24255)
            MAX-ACCESS read-only
            STATUS current
            DESCRIPTION
                "SSU device ID. Value range: 024'001 to 024'255, in which the first digits indicate the device type and the last three digits indicate the device SN."
            ::= { hwSSUEntry 2 }

        hwSSUEquipName OBJECT-TYPE
            SYNTAX OCTET STRING (SIZE (0..63))
            MAX-ACCESS read-only
            STATUS current
            DESCRIPTION
                "Device name of the SSU module, character string type, is used to specify the SSU module. 
                Otherwise, the configured character can not be any other languages except English."
            ::= { hwSSUEntry 3 }

        hwSSURunningState OBJECT-TYPE
            SYNTAX INTEGER
                {
                on(1),
                off(2),
                nullOper(255)
                }
            MAX-ACCESS read-only
            STATUS current
            DESCRIPTION
                "The running status of the SSU module. It is an enumeration type: 
                  If the enumeration value is 1, it indicates that the SSU module is power on ;
                  If the enumeration value is 2, it indicates that the SSU module is power off;
                 If the enumeration value is 255, it indicates that the SSU module is nulloper;   "
            ::= { hwSSUEntry 4 }

        hwSSUInputVoltage OBJECT-TYPE
            SYNTAX Unsigned32 (0..2000)
            MAX-ACCESS read-only
            STATUS current
            DESCRIPTION
                "The input voltage of SSU, 
                Value range: 0 to 200, 
                units: V, 
                and the value is one decimal space (.1)."
            ::= { hwSSUEntry 5 }

        hwSSUOutputVoltage OBJECT-TYPE
            SYNTAX Unsigned32 (0..2000)
            MAX-ACCESS read-only
            STATUS current
            DESCRIPTION
                "The output voltage of SSU, 
                Value range: 0 to 200, 
                units: V, 
                and the value is one decimal space (.1)."
            ::= { hwSSUEntry 6 }

        hwSSUOutputCurrent OBJECT-TYPE
            SYNTAX Unsigned32 (0..10000)
            MAX-ACCESS read-only
            STATUS current
            DESCRIPTION
                "The output current of SSU, 
                Value range: 0 to 1000, 
                units: A, 
                and the value is one decimal space (.1)."
            ::= { hwSSUEntry 7 }

        hwSSUAddress OBJECT-TYPE
            SYNTAX Unsigned32 (0..100   )
            MAX-ACCESS read-only
            STATUS current
            DESCRIPTION
                "The address of SSU, 
                Value range: 0 to 100, 
                units: , 
                and the value is  an integer (1)."
            ::= { hwSSUEntry 8 }

        hwSSURowStatus OBJECT-TYPE
            SYNTAX RowStatus
            MAX-ACCESS read-create
            STATUS current
            DESCRIPTION
                "RowStatus fo SSU."
            ::= { hwSSUEntry 100 }

        hwSiteBatteryCabinets OBJECT IDENTIFIER ::= { hwSiteMonitorMIBObjects 14 }

        hwSiteBatteryCabinetEquip OBJECT IDENTIFIER ::= { hwSiteBatteryCabinets 2 }

        hwSiteBatteryCabinetTable OBJECT-TYPE
            SYNTAX SEQUENCE OF HwSiteBatteryCabinetEntry
            MAX-ACCESS not-accessible
             STATUS current
             DESCRIPTION
                "/"
            ::= { hwSiteBatteryCabinetEquip 1 }

        hwSiteBatteryCabinetEntry OBJECT-TYPE
                        SYNTAX HwSiteBatteryCabinetEntry
            MAX-ACCESS not-accessible
             STATUS current
             DESCRIPTION
                "/"
            INDEX { hwBatteryCabinetIndex }
            ::= { hwSiteBatteryCabinetTable 1 }

        HwSiteBatteryCabinetEntry            ::= SEQUENCE {
                hwBatteryCabinetIndex
                    Unsigned32,
                hwBatteryCabinetEquipId
                    Unsigned32,
                hwBatteryCabinetEquipName
                    OCTET STRING,
                hwBatteryCabinetIndoorVentTemp
                    Integer32,
                hwBatteryCabinetBattTemp
                    Integer32,
                hwBatteryCabinetFan1Speed
                    Integer32,
                hwBatteryCabinetFan2Speed
                    Integer32,
                hwBatteryCabinetFan3Speed
                    Integer32,
                hwBatteryCabinetFan4Speed
                    Integer32,
                hwBatteryCabinetAirConditionerStatus
                    INTEGER,
                hwBatteryCabinetCompressorStatus
                    INTEGER,
                hwBatteryCabinetInternalFanSpeed
                    Integer32,
                hwBatteryCabinetExternalFanSpeed
                    Integer32,
                hwBatteryCabinetAirConditionerRuntime
                    Unsigned32,
                hwBatteryCabinetCompressorRuntime
                    Unsigned32,
                hwBatteryCabinetAirConWorkTemp
                    Integer32,
                hwBatteryCabinetAirConStopTemp
                    Integer32,
                hwBatteryCabinetOperStatus
                    INTEGER,
                hwBatteryCabinetRowStatus
                    RowStatus
            }

        hwBatteryCabinetIndex OBJECT-TYPE
            SYNTAX Unsigned32 (4096..20479)
            MAX-ACCESS read-only
            STATUS current
            DESCRIPTION
                "Battery Cabinet table index,which value is according to the actual subject. Lines of the device list are restricted by the quantity of Battery Cabinet"
            ::= { hwSiteBatteryCabinetEntry 1 }

        hwBatteryCabinetEquipId OBJECT-TYPE
            SYNTAX Unsigned32 (25000..25255)
            MAX-ACCESS read-only
            STATUS current
            DESCRIPTION
                "Battery Cabinet device ID. Value range: 025'001 to 025'255, in which the first digits indicate the device type and the last three digits indicate the device SN."
            ::= { hwSiteBatteryCabinetEntry 2 }

        hwBatteryCabinetEquipName OBJECT-TYPE
            SYNTAX OCTET STRING (SIZE (0..63))
            MAX-ACCESS read-only
            STATUS current
            DESCRIPTION
                "Battery Cabinet name, of the character string type, is used to specify battery cabinet. Users can configure it.
                Otherwise, the configured character can not be any other languages except English.
                "
            ::= { hwSiteBatteryCabinetEntry 3 }

        hwBatteryCabinetIndoorVentTemp OBJECT-TYPE
            SYNTAX Integer32 ( -40..100)
            MAX-ACCESS read-only
            STATUS current
            DESCRIPTION
                "Indoor vent temperature. It is an environment parameter collected in real time. 
                Value range: -40 to +100, 
                units: centigrade, 
                and the value is an integer (1).  
                If the value is -99999, it indicates that the temperature sensor is not configured."
            ::= { hwSiteBatteryCabinetEntry 4 }

        hwBatteryCabinetBattTemp OBJECT-TYPE
            SYNTAX Integer32 ( -40..100)
            MAX-ACCESS read-only
            STATUS current
            DESCRIPTION
                "Battery temperature. It is an environment parameter collected in real time.
                Value range: -40 to +100, 
                units: centigrade, 
                and the value is an integer (1).  
                If the value is -99999, it indicates that the temperature sensor is not configured."
            ::= { hwSiteBatteryCabinetEntry 5 }

        hwBatteryCabinetFan1Speed OBJECT-TYPE
            SYNTAX Integer32 (0..10000)
            MAX-ACCESS read-only
            STATUS current
            DESCRIPTION
                "Fan 1 speed, 
                Value range: 0.0 to 10000.0.
                Unit: rpm,
                the value is an integer (1). 
                If the value is -1, it indicates that the fan is not configured."
            ::= { hwSiteBatteryCabinetEntry 6 }

        hwBatteryCabinetFan2Speed OBJECT-TYPE
            SYNTAX Integer32 (0..10000)
            MAX-ACCESS read-only
            STATUS current
            DESCRIPTION
                "Fan 2 speed, 
                Value range: 0.0 to 10000.0.
                Unit: rpm,
                the value is an integer (1). 
                If the value is -1, it indicates that the fan is not configured."
            ::= { hwSiteBatteryCabinetEntry 7 }

        hwBatteryCabinetFan3Speed OBJECT-TYPE
            SYNTAX Integer32 (0..10000)
            MAX-ACCESS read-only
            STATUS current
            DESCRIPTION
                "Fan 3 speed, 
                Value range: 0.0 to 10000.0.
                Unit: rpm,
                the value is an integer (1). 
                If the value is -1, it indicates that the fan is not configured."
            ::= { hwSiteBatteryCabinetEntry 8 }

        hwBatteryCabinetFan4Speed OBJECT-TYPE
            SYNTAX Integer32 (0..10000)
            MAX-ACCESS read-only
            STATUS current
            DESCRIPTION
                "Fan 4 speed, 
                Value range: 0.0 to 10000.0.
                Unit: rpm,
                the value is an integer (1). 
                If the value is -1, it indicates that the fan is not configured."
            ::= { hwSiteBatteryCabinetEntry 9 }

        hwBatteryCabinetAirConditionerStatus OBJECT-TYPE
            SYNTAX INTEGER
                {
                standby(1),
                run(2),
                fault(3),
                unknown(255)
                }
            MAX-ACCESS read-only
            STATUS current
            DESCRIPTION
                "State of the airconditioner. It is an enumeration type: 
                If the enumeration value is 1, it indicates that the airconditioner is in the standby state;
                If the enumeration value is 2, it indicates that the airconditioner is in the run state;  
                If the enumeration value is 3, it indicates that the airconditioner is in the fault state;  
                If the enumeration value is 255, it indicates airconditioner status unknown. "
            ::= { hwSiteBatteryCabinetEntry 10 }

        hwBatteryCabinetCompressorStatus OBJECT-TYPE
            SYNTAX INTEGER
                {
                standby(1),
                run(2),
                fault(3),
                unknown(255)
                }
            MAX-ACCESS read-only
            STATUS current
            DESCRIPTION
                "State of the compressor. It is an enumeration type: 
                If the enumeration value is 1, it indicates that the compressor is in the standby state;
                If the enumeration value is 2, it indicates that the compressor is in the run state;  
                If the enumeration value is 3, it indicates that the compressor is in the fault state;  
                If the enumeration value is 255, it indicates compressor operation status unknown. "
            ::= { hwSiteBatteryCabinetEntry 11 }

        hwBatteryCabinetInternalFanSpeed OBJECT-TYPE
            SYNTAX Integer32 (0..10000)
            MAX-ACCESS read-only
            STATUS current
            DESCRIPTION
                "Internal Fan speed,
                Value range: 0 to 10000.
                Unit: rpm,
                the value is an integer (1). 
                If the value is -1, it indicates that the fan is not configured."
            ::= { hwSiteBatteryCabinetEntry 12 }

        hwBatteryCabinetExternalFanSpeed OBJECT-TYPE
            SYNTAX Integer32 (0..10000)
            MAX-ACCESS read-only
            STATUS current
            DESCRIPTION
                "External Fan speed, 
                Value range: 0 to 10000.
                Unit: rpm,
                the value is an integer (1). 
                If the value is -1, it indicates that the temperature sensor is not configured."
            ::= { hwSiteBatteryCabinetEntry 13 }

        hwBatteryCabinetAirConditionerRuntime OBJECT-TYPE
            SYNTAX Unsigned32
            MAX-ACCESS read-only
            STATUS current
            DESCRIPTION
                "Total runtime of the air conditioner. 
                Value units: hour (h), 
                and the value is an integer (1). 
                If the value is 2147483647(0x7FFFFFFF), it indicates that the value is invalid."
            ::= { hwSiteBatteryCabinetEntry 14 }

        hwBatteryCabinetCompressorRuntime OBJECT-TYPE
            SYNTAX Unsigned32
            MAX-ACCESS read-only
            STATUS current
            DESCRIPTION
                "Total runtime of the compressor. 
                Value units: hour (h), 
                and the value is an integer (1). 
                If the value is 2147483647(0x7FFFFFFF), it indicates that the value is invalid."
            ::= { hwSiteBatteryCabinetEntry 15 }

        hwBatteryCabinetAirConWorkTemp OBJECT-TYPE
            SYNTAX Integer32 ( -20..80)
            MAX-ACCESS read-write
            STATUS current
            DESCRIPTION
                "Battery cabinet aircondition power on temperature point, 
                Value range:-20 to 80 
                Unit: degC.
                and the value is an integer (1)."
            ::= { hwSiteBatteryCabinetEntry 16 }

        hwBatteryCabinetAirConStopTemp OBJECT-TYPE
            SYNTAX Integer32 ( -20..80)
            MAX-ACCESS read-write
            STATUS current
            DESCRIPTION
                "Battery cabinet aircondition power off temperature point, 
                Value range:-20 to 80 
                Unit: degC.
                and the value is an integer(1)."
            ::= { hwSiteBatteryCabinetEntry 17 }

        hwBatteryCabinetOperStatus OBJECT-TYPE
            SYNTAX INTEGER
                {
                normal(1),
                fault(2),
                unknown(255)
                }
            MAX-ACCESS read-only
            STATUS current
            DESCRIPTION
                "State of the Battery Cabinet. It is an enumeration type: 
                If the enumeration value is 1, it indicates that the Inverter is in the normal state;
                If the enumeration value is 2, it indicates that the Inverter is in the fault state;  
                If the enumeration value is 255, it indicates that the Inverter is in the unknown state;  "
            ::= { hwSiteBatteryCabinetEntry 99 }

        hwBatteryCabinetRowStatus OBJECT-TYPE
            SYNTAX RowStatus
            MAX-ACCESS read-create
            STATUS current
            DESCRIPTION
                "RowStatus fo Battery Cabinet table."
            ::= { hwSiteBatteryCabinetEntry 100 }

        hwSiteEsdu OBJECT IDENTIFIER ::= { hwSiteMonitorMIBObjects 15 }

        hwEsduTable OBJECT-TYPE
            SYNTAX SEQUENCE OF HwEsduEntry
            MAX-ACCESS not-accessible
             STATUS current
             DESCRIPTION
                "/"
            ::= { hwSiteEsdu 2 }

        hwEsduEntry OBJECT-TYPE
                        SYNTAX HwEsduEntry
            MAX-ACCESS not-accessible
             STATUS current
             DESCRIPTION
                "/"
            INDEX { hwEsduIndex }
            ::= { hwEsduTable 1 }

        HwEsduEntry            ::= SEQUENCE {
                hwEsduIndex
                    Unsigned32,
                hwEsduEquipId
                    Unsigned32,
                hwEsduEquipName
                    OCTET STRING,
                hwEsduSetDigitalInput1AlarmCondition
                    INTEGER,
                hwEsduDigitalInput1OperStatus
                    INTEGER,
                hwEsduSetDigitalInput2AlarmCondition
                    INTEGER,
                hwEsduDigitalInput2OperStatus
                    INTEGER,
                hwEsduSetDigitalInput3AlarmCondition
                    INTEGER,
                hwEsduDigitalInput3OperStatus
                    INTEGER,
                hwEsduSetDigitalInput4AlarmCondition
                    INTEGER,
                hwEsduDigitalInput4OperStatus
                    INTEGER,
                hwEsduSetDigitalInput5AlarmCondition
                    INTEGER,
                hwEsduDigitalInput5OperStatus
                    INTEGER,
                hwEsduSetDigitalInput6AlarmCondition
                    INTEGER,
                hwEsduDigitalInput6OperStatus
                    INTEGER,
                hwEsduSetDigitalInput7AlarmCondition
                    INTEGER,
                hwEsduDigitalInput7OperStatus
                    INTEGER,
                hwEsduSetDigitalInput8AlarmCondition
                    INTEGER,
                hwEsduDigitalInput8OperStatus
                    INTEGER,
                hwEsduSetDigitalInput9AlarmCondition
                    INTEGER,
                hwEsduDigitalInput9OperStatus
                    INTEGER,
                hwEsduSetDigitalInput10AlarmCondition
                    INTEGER,
                hwEsduDigitalInput10OperStatus
                    INTEGER,
                hwEsduSetDigitalInput11AlarmCondition
                    INTEGER,
                hwEsduDigitalInput11OperStatus
                    INTEGER,
                hwEsduSetDigitalInput12AlarmCondition
                    INTEGER,
                hwEsduDigitalInput12OperStatus
                    INTEGER,
                hwEsduBtempValue
                    Integer32,
                hwEsduBtempOperStatus
                    INTEGER,
                hwEsduTemp1Value
                    Integer32,
                hwEsduTemp1HighLimit
                    Integer32,
                hwEsduTemp1LowLimit
                    Integer32,
                hwEsduTemp1OperStatus
                    INTEGER,
                hwEsduTemp2Value
                    Integer32,
                hwEsduTemp2HighLimit
                    Integer32,
                hwEsduTemp2LowLimit
                    Integer32,
                hwEsduTemp2OperStatus
                    INTEGER,
                hwEsduDoorSensorConnect
                    INTEGER
            }

        hwEsduIndex OBJECT-TYPE
            SYNTAX Unsigned32 (3428..3443)
            MAX-ACCESS read-only
            STATUS current
            DESCRIPTION
                "ESDU equip index,which value is according to the actual subject. Lines of the device list are restricted by the quantity of Battery Cabinet"
            ::= { hwEsduEntry 1 }

        hwEsduEquipId OBJECT-TYPE
            SYNTAX Unsigned32 (28001..28255)
            MAX-ACCESS read-only
            STATUS current
            DESCRIPTION
                "Esdu device ID. Value range: 028,001 to 028,255, in which the first digits indicate the device type and the last three digits indicate the device SN."
            ::= { hwEsduEntry 2 }

        hwEsduEquipName OBJECT-TYPE
            SYNTAX OCTET STRING (SIZE (0..63))
            MAX-ACCESS read-only
            STATUS current
            DESCRIPTION
                "/"
            ::= { hwEsduEntry 3 }

        hwEsduSetDigitalInput1AlarmCondition OBJECT-TYPE
            SYNTAX INTEGER
                {
                close(1),
                open(2),
                unknown(255)
                }
            MAX-ACCESS read-write
            STATUS current
            DESCRIPTION
                "Spare digital alarm state. It is an enumeration value.
                If the value of the node is 1, it indicates a high-tension alarm;
                If the value of the node is 2, it indicates a low-tension alarm;
                If the value of the node is 255, it indicates airconditioner status unknown."
            ::= { hwEsduEntry 4 }

        hwEsduDigitalInput1OperStatus OBJECT-TYPE
            SYNTAX INTEGER
                {
                normal(1),
                alarm(2),
                alarmResume(254),
                unknown(255)
                }
            MAX-ACCESS read-only
            STATUS current
            DESCRIPTION
                "It indicates the digital input operation status. It is an enumeration value.
                If the value of the node is 1, it indicates that the diesel of state is normal;
                If the value of the node is 2, it indicates that the diesel of state is alarm;
                If the value of the node is 254, it indicates that the diesel of state is alarmResume;
                If the value of the node is 255, it indicates that the diesel of state is unknown;"
            ::= { hwEsduEntry 5 }

        hwEsduSetDigitalInput2AlarmCondition OBJECT-TYPE
            SYNTAX INTEGER
                {
                close(1),
                open(2),
                unknown(255)
                }
            MAX-ACCESS read-write
            STATUS current
            DESCRIPTION
                "Spare digital alarm state. It is an enumeration value.
                If the value of the node is 1, it indicates a high-tension alarm;
                If the value of the node is 2, it indicates a low-tension alarm;
                If the value of the node is 255, it indicates airconditioner status unknown."
            ::= { hwEsduEntry 6 }

        hwEsduDigitalInput2OperStatus OBJECT-TYPE
            SYNTAX INTEGER
                {
                normal(1),
                alarm(2),
                alarmResume(254),
                unknown(255)
                }
            MAX-ACCESS read-only
            STATUS current
            DESCRIPTION
                "It indicates the digital input operation status. It is an enumeration value.
                If the value of the node is 1, it indicates that the diesel of state is normal;
                If the value of the node is 2, it indicates that the diesel of state is alarm;
                If the value of the node is 254, it indicates that the diesel of state is alarmResume;
                If the value of the node is 255, it indicates that the diesel of state is unknown;"
            ::= { hwEsduEntry 7 }

        hwEsduSetDigitalInput3AlarmCondition OBJECT-TYPE
            SYNTAX INTEGER
                {
                close(1),
                open(2),
                unknown(255)
                }
            MAX-ACCESS read-write
            STATUS current
            DESCRIPTION
                "Spare digital alarm state. It is an enumeration value.
                If the value of the node is 1, it indicates a high-tension alarm;
                If the value of the node is 2, it indicates a low-tension alarm;
                If the value of the node is 255, it indicates airconditioner status unknown."
            ::= { hwEsduEntry 8 }

        hwEsduDigitalInput3OperStatus OBJECT-TYPE
            SYNTAX INTEGER
                {
                normal(1),
                alarm(2),
                alarmResume(254),
                unknown(255)
                }
            MAX-ACCESS read-only
            STATUS current
            DESCRIPTION
                "It indicates the digital input operation status. It is an enumeration value.
                If the value of the node is 1, it indicates that the diesel of state is normal;
                If the value of the node is 2, it indicates that the diesel of state is alarm;
                If the value of the node is 254, it indicates that the diesel of state is alarmResume;
                If the value of the node is 255, it indicates that the diesel of state is unknown;"
            ::= { hwEsduEntry 9 }

        hwEsduSetDigitalInput4AlarmCondition OBJECT-TYPE
            SYNTAX INTEGER
                {
                close(1),
                open(2),
                unknown(255)
                }
            MAX-ACCESS read-write
            STATUS current
            DESCRIPTION
                "Spare digital alarm state. It is an enumeration value.
                If the value of the node is 1, it indicates a high-tension alarm;
                If the value of the node is 2, it indicates a low-tension alarm;
                If the value of the node is 255, it indicates airconditioner status unknown."
            ::= { hwEsduEntry 10 }

        hwEsduDigitalInput4OperStatus OBJECT-TYPE
            SYNTAX INTEGER
                {
                normal(1),
                alarm(2),
                alarmResume(254),
                unknown(255)
                }
            MAX-ACCESS read-only
            STATUS current
            DESCRIPTION
                "It indicates the digital input operation status. It is an enumeration value.
                If the value of the node is 1, it indicates that the diesel of state is normal;
                If the value of the node is 2, it indicates that the diesel of state is alarm;
                If the value of the node is 254, it indicates that the diesel of state is alarmResume;
                If the value of the node is 255, it indicates that the diesel of state is unknown;"
            ::= { hwEsduEntry 11 }

        hwEsduSetDigitalInput5AlarmCondition OBJECT-TYPE
            SYNTAX INTEGER
                {
                close(1),
                open(2),
                unknown(255)
                }
            MAX-ACCESS read-write
            STATUS current
            DESCRIPTION
                "Spare digital alarm state. It is an enumeration value.
                If the value of the node is 1, it indicates a high-tension alarm;
                If the value of the node is 2, it indicates a low-tension alarm;
                If the value of the node is 255, it indicates airconditioner status unknown."
            ::= { hwEsduEntry 12 }

        hwEsduDigitalInput5OperStatus OBJECT-TYPE
            SYNTAX INTEGER
                {
                normal(1),
                alarm(2),
                alarmResume(254),
                unknown(255)
                }
            MAX-ACCESS read-only
            STATUS current
            DESCRIPTION
                "It indicates the digital input operation status. It is an enumeration value.
                If the value of the node is 1, it indicates that the diesel of state is normal;
                If the value of the node is 2, it indicates that the diesel of state is alarm;
                If the value of the node is 254, it indicates that the diesel of state is alarmResume;
                If the value of the node is 255, it indicates that the diesel of state is unknown;"
            ::= { hwEsduEntry 13 }

        hwEsduSetDigitalInput6AlarmCondition OBJECT-TYPE
            SYNTAX INTEGER
                {
                close(1),
                open(2),
                unknown(255)
                }
            MAX-ACCESS read-write
            STATUS current
            DESCRIPTION
                "Spare digital alarm state. It is an enumeration value.If the value of the node is 1, it indicates a high-tension alarm;If the value of the node is 2, it indicates a low-tension alarm;If the value of the node is 255, it indicates airconditioner status unknown."
            ::= { hwEsduEntry 14 }

        hwEsduDigitalInput6OperStatus OBJECT-TYPE
            SYNTAX INTEGER
                {
                normal(1),
                alarm(2),
                alarmResume(254),
                unknown(255)
                }
            MAX-ACCESS read-only
            STATUS current
            DESCRIPTION
                "It indicates the digital input operation status. It is an enumeration value.
                If the value of the node is 1, it indicates that the diesel of state is normal;
                If the value of the node is 2, it indicates that the diesel of state is alarm;
                If the value of the node is 254, it indicates that the diesel of state is alarmResume;
                If the value of the node is 255, it indicates that the diesel of state is unknown;"
            ::= { hwEsduEntry 15 }

        hwEsduSetDigitalInput7AlarmCondition OBJECT-TYPE
            SYNTAX INTEGER
                {
                close(1),
                open(2),
                unknown(255)
                }
            MAX-ACCESS read-write
            STATUS current
            DESCRIPTION
                "Spare digital alarm state. It is an enumeration value.
                If the value of the node is 1, it indicates a high-tension alarm;
                If the value of the node is 2, it indicates a low-tension alarm;
                If the value of the node is 255, it indicates airconditioner status unknown."
            ::= { hwEsduEntry 16 }

        hwEsduDigitalInput7OperStatus OBJECT-TYPE
            SYNTAX INTEGER
                {
                normal(1),
                alarm(2),
                alarmResume(254),
                unknown(255)
                }
            MAX-ACCESS read-only
            STATUS current
            DESCRIPTION
                "It indicates the digital input operation status. It is an enumeration value.
                If the value of the node is 1, it indicates that the diesel of state is normal;
                If the value of the node is 2, it indicates that the diesel of state is alarm;
                If the value of the node is 254, it indicates that the diesel of state is alarmResume;
                If the value of the node is 255, it indicates that the diesel of state is unknown;"
            ::= { hwEsduEntry 17 }

        hwEsduSetDigitalInput8AlarmCondition OBJECT-TYPE
            SYNTAX INTEGER
                {
                close(1),
                open(2),
                unknown(255)
                }
            MAX-ACCESS read-write
            STATUS current
            DESCRIPTION
                "Spare digital alarm state. It is an enumeration value.
                If the value of the node is 1, it indicates a high-tension alarm;
                If the value of the node is 2, it indicates a low-tension alarm;
                If the value of the node is 255, it indicates airconditioner status unknown."
            ::= { hwEsduEntry 18 }

        hwEsduDigitalInput8OperStatus OBJECT-TYPE
            SYNTAX INTEGER
                {
                normal(1),
                alarm(2),
                alarmResume(254),
                unknown(255)
                }
            MAX-ACCESS read-only
            STATUS current
            DESCRIPTION
                "It indicates the digital input operation status. It is an enumeration value.
                If the value of the node is 1, it indicates that the diesel of state is normal;
                If the value of the node is 2, it indicates that the diesel of state is alarm;
                If the value of the node is 254, it indicates that the diesel of state is alarmResume;
                If the value of the node is 255, it indicates that the diesel of state is unknown;"
            ::= { hwEsduEntry 19 }

        hwEsduSetDigitalInput9AlarmCondition OBJECT-TYPE
            SYNTAX INTEGER
                {
                close(1),
                open(2),
                unknown(255)
                }
            MAX-ACCESS read-write
            STATUS current
            DESCRIPTION
                "Spare digital alarm state. It is an enumeration value.
                If the value of the node is 1, it indicates a high-tension alarm;
                If the value of the node is 2, it indicates a low-tension alarm;
                If the value of the node is 255, it indicates airconditioner status unknown."
            ::= { hwEsduEntry 20 }

        hwEsduDigitalInput9OperStatus OBJECT-TYPE
            SYNTAX INTEGER
                {
                normal(1),
                alarm(2),
                alarmResume(254),
                unknown(255)
                }
            MAX-ACCESS read-only
            STATUS current
            DESCRIPTION
                "It indicates the digital input operation status. It is an enumeration value.
                If the value of the node is 1, it indicates that the diesel of state is normal;
                If the value of the node is 2, it indicates that the diesel of state is alarm;
                If the value of the node is 254, it indicates that the diesel of state is alarmResume;
                If the value of the node is 255, it indicates that the diesel of state is unknown;"
            ::= { hwEsduEntry 21 }

        hwEsduSetDigitalInput10AlarmCondition OBJECT-TYPE
            SYNTAX INTEGER
                {
                close(1),
                open(2),
                unknown(255)
                }
            MAX-ACCESS read-write
            STATUS current
            DESCRIPTION
                "Spare digital alarm state. It is an enumeration value.
                If the value of the node is 1, it indicates a high-tension alarm;
                If the value of the node is 2, it indicates a low-tension alarm;
                If the value of the node is 255, it indicates airconditioner status unknown."
            ::= { hwEsduEntry 22 }

        hwEsduDigitalInput10OperStatus OBJECT-TYPE
            SYNTAX INTEGER
                {
                normal(1),
                alarm(2),
                alarmResume(254),
                unknown(255)
                }
            MAX-ACCESS read-only
            STATUS current
            DESCRIPTION
                "It indicates the digital input operation status. It is an enumeration value.
                If the value of the node is 1, it indicates that the diesel of state is normal;
                If the value of the node is 2, it indicates that the diesel of state is alarm;
                If the value of the node is 254, it indicates that the diesel of state is alarmResume;
                If the value of the node is 255, it indicates that the diesel of state is unknown;"
            ::= { hwEsduEntry 23 }

        hwEsduSetDigitalInput11AlarmCondition OBJECT-TYPE
            SYNTAX INTEGER
                {
                close(1),
                open(2),
                unknown(255)
                }
            MAX-ACCESS read-write
            STATUS current
            DESCRIPTION
                "Spare digital alarm state. It is an enumeration value.
                If the value of the node is 1, it indicates a high-tension alarm;
                If the value of the node is 2, it indicates a low-tension alarm;
                If the value of the node is 255, it indicates airconditioner status unknown."
            ::= { hwEsduEntry 24 }

        hwEsduDigitalInput11OperStatus OBJECT-TYPE
            SYNTAX INTEGER
                {
                normal(1),
                alarm(2),
                alarmResume(254),
                unknown(255)
                }
            MAX-ACCESS read-only
            STATUS current
            DESCRIPTION
                "It indicates the digital input operation status. It is an enumeration value.
                If the value of the node is 1, it indicates that the diesel of state is normal;
                If the value of the node is 2, it indicates that the diesel of state is alarm;
                If the value of the node is 254, it indicates that the diesel of state is alarmResume;
                If the value of the node is 255, it indicates that the diesel of state is unknown;"
            ::= { hwEsduEntry 25 }

        hwEsduSetDigitalInput12AlarmCondition OBJECT-TYPE
            SYNTAX INTEGER
                {
                close(1),
                open(2),
                unknown(255)
                }
            MAX-ACCESS read-write
            STATUS current
            DESCRIPTION
                "Spare digital alarm state. It is an enumeration value.
                If the value of the node is 1, it indicates a high-tension alarm;
                If the value of the node is 2, it indicates a low-tension alarm;
                If the value of the node is 255, it indicates airconditioner status unknown."
            ::= { hwEsduEntry 26 }

        hwEsduDigitalInput12OperStatus OBJECT-TYPE
            SYNTAX INTEGER
                {
                normal(1),
                alarm(2),
                alarmResume(254),
                unknown(255)
                }
            MAX-ACCESS read-only
            STATUS current
            DESCRIPTION
                "It indicates the digital input operation status. It is an enumeration value.
                If the value of the node is 1, it indicates that the diesel of state is normal;
                If the value of the node is 2, it indicates that the diesel of state is alarm;
                If the value of the node is 254, it indicates that the diesel of state is alarmResume;
                If the value of the node is 255, it indicates that the diesel of state is unknown;"
            ::= { hwEsduEntry 27 }

        hwEsduBtempValue OBJECT-TYPE
            SYNTAX Integer32 ( -40..80)
            MAX-ACCESS read-only
            STATUS current
            DESCRIPTION
                "Temp1. It is an environment parameter collected in real time. 
                Value range: -40 to +80, 
                Unit: degC
                and the value is an integer (1).  
                If the value is -1024, it indicates that the temperature sensor is not configured."
            ::= { hwEsduEntry 28 }

        hwEsduBtempOperStatus OBJECT-TYPE
            SYNTAX INTEGER
                {
                normal(1),
                tempHigh(2),
                tempLow(3),
                notInslot(4),
                tempFault(5),
                alarmResume(254),
                unknown(255)
                }
            MAX-ACCESS read-only
            STATUS current
            DESCRIPTION
                "State of the site temp1 sensor. It is an enumeration type: 
                  If the enumeration value is 1, it indicates that the site temp1 sensor is in the normal state; 
                  If the enumeration value is 2, it indicates that the temp1 sensor is over temperature; 
                  If the enumeration value is 3, it indicates that the temp1 sensor is under temperature; 
                  If the enumeration value is 4, it indicates that the temp1 sensor is not in slot;
                  If the enumeration value is 5, it indicates that the temp1 sensor is fault;
                  If the enumeration value is 254, it indicates that temp1 alarm resume; 
                  If the enumeration value is 255, it indicates temp1 sensor operation status unknown."
            ::= { hwEsduEntry 31 }

        hwEsduTemp1Value OBJECT-TYPE
            SYNTAX Integer32 ( -40..80)
            MAX-ACCESS read-only
            STATUS current
            DESCRIPTION
                "Temp1. It is an environment parameter collected in real time. 
                Value range: -40 to +80, 
                units: centigrade (degC), 
                and the value is an integer (1).  
                If the value is -1024, it indicates that the temperature sensor is not configured."
            ::= { hwEsduEntry 32 }

        hwEsduTemp1HighLimit OBJECT-TYPE
            SYNTAX Integer32 (25..80)
            MAX-ACCESS read-write
            STATUS current
            DESCRIPTION
                "Upper threshold of the temp1 alarm, can be configured by users. 
                Value range: 25 to 80, 
                units: centigrade (degC), 
                and the value is an integer (1).  
                If the value is 2147483647(0x7FFFFFFF), it indicates that the value is invalid."
            ::= { hwEsduEntry 33 }

        hwEsduTemp1LowLimit OBJECT-TYPE
            SYNTAX Integer32 ( -20..20)
            MAX-ACCESS read-write
            STATUS current
            DESCRIPTION
                "Lower threshold of the temp1 alarm, can be configured by users. 
                Value range: -20 to 20, 
                units: centigrade (degC), 
                and the value is an integer (1).  
                If the value is 2147483647(0x7FFFFFFF), it indicates that the value is invalid."
            ::= { hwEsduEntry 34 }

        hwEsduTemp1OperStatus OBJECT-TYPE
            SYNTAX INTEGER
                {
                normal(1),
                tempHigh(2),
                tempLow(3),
                notInslot(4),
                tempFault(5),
                alarmResume(254),
                unknown(255)
                }
            MAX-ACCESS read-only
            STATUS current
            DESCRIPTION
                "State of the site temp1 sensor. It is an enumeration type: 
                  If the enumeration value is 1, it indicates that the site temp1 sensor is in the normal state; 
                  If the enumeration value is 2, it indicates that the temp1 sensor is over temperature; 
                  If the enumeration value is 3, it indicates that the temp1 sensor is under temperature; 
                  If the enumeration value is 4, it indicates that the temp1 sensor is not in slot;
                  If the enumeration value is 5, it indicates that the temp1 sensor is fault;
                  If the enumeration value is 254, it indicates that temp1 alarm resume; 
                  If the enumeration value is 255, it indicates temp1 sensor operation status unknown."
            ::= { hwEsduEntry 35 }

        hwEsduTemp2Value OBJECT-TYPE
            SYNTAX Integer32 ( -40..80)
            MAX-ACCESS read-only
            STATUS current
            DESCRIPTION
                "Temp2. It is an environment parameter collected in real time. 
                Value range: -40 to +80, 
                units: centigrade (degC), 
                and the value is an integer (1).  
                If the value is -1024, it indicates that the temperature sensor is not configured."
            ::= { hwEsduEntry 36 }

        hwEsduTemp2HighLimit OBJECT-TYPE
            SYNTAX Integer32 (25..80)
            MAX-ACCESS read-write
            STATUS current
            DESCRIPTION
                "Upper threshold of the temp2 alarm, can be configured by users. 
                Value range: 25 to 80, 
                units: centigrade (degC), 
                and the value is an integer (1).  
                If the value is 2147483647(0x7FFFFFFF), it indicates that the value is invalid."
            ::= { hwEsduEntry 37 }

        hwEsduTemp2LowLimit OBJECT-TYPE
            SYNTAX Integer32 ( -20..20)
            MAX-ACCESS read-write
            STATUS current
            DESCRIPTION
                "Lower threshold of the temp2 alarm, can be configured by users. 
                Value range: -20 to 20,
                 units: centigrade (degC), 
                and the value is an integer (1).  
                If the value is 2147483647(0x7FFFFFFF), it indicates that the value is invalid."
            ::= { hwEsduEntry 38 }

        hwEsduTemp2OperStatus OBJECT-TYPE
            SYNTAX INTEGER
                {
                normal(1),
                tempHigh(2),
                tempLow(3),
                notInslot(4),
                tempFault(5),
                alarmResume(254),
                unknown(255)
                }
            MAX-ACCESS read-only
            STATUS current
            DESCRIPTION
                "State of the site temp2 sensor. It is an enumeration type: 
                  If the enumeration value is 1, it indicates that the site temp2 sensor is in the normal state; 
                  If the enumeration value is 2, it indicates that the temp2 sensor is over temperature; 
                  If the enumeration value is 3, it indicates that the temp2 sensor is under temperature; 
                  If the enumeration value is 4, it indicates that the temp2 sensor is not in slot;
                  If the enumeration value is 5, it indicates that the temp2 sensor is fault;
                  If the enumeration value is 254, it indicates that temp2 alarm resume; 
                  If the enumeration value is 255, it indicates temp2 sensor operation status unknown."
            ::= { hwEsduEntry 39 }

        hwEsduDoorSensorConnect OBJECT-TYPE
            SYNTAX INTEGER
                {
                disable(1),enable(2),unknown(255)
                }
            MAX-ACCESS read-write
            STATUS current
            DESCRIPTION
                "Door Sensor Connected; It is an enumeration value, and can be configured. 
                If the enumeration value is 1, it indicates Door Sensor is disable;
                If the enumeration value is 2, it indicates Door Sensor is enalble;
                If the enumeration value is 255, it indicates timed boost charge is unknown. "
            ::= { hwEsduEntry 40 }

        hwSiteIbox OBJECT IDENTIFIER ::= { hwSiteMonitorMIBObjects 20 }

        hwSiteIboxTable OBJECT-TYPE
            SYNTAX SEQUENCE OF HwSiteIboxEntry
            MAX-ACCESS not-accessible
             STATUS current
             DESCRIPTION
                "/"
            ::= { hwSiteIbox 1 }

        hwSiteIboxEntry OBJECT-TYPE
                        SYNTAX HwSiteIboxEntry
            MAX-ACCESS not-accessible
             STATUS current
             DESCRIPTION
                "/"
            INDEX { hwIboxIndex }
            ::= { hwSiteIboxTable 1 }

        HwSiteIboxEntry            ::= SEQUENCE {
                hwIboxIndex
                    Unsigned32,
                hwIboxEquipId
                    Unsigned32,
                hwIboxEquipName
                    OCTET STRING,
                hwIbatEquipNum
                    Unsigned32
            }

        hwIboxIndex OBJECT-TYPE
            SYNTAX Unsigned32 (560..575)
            MAX-ACCESS read-only
            STATUS current
            DESCRIPTION
                "ibox table index,which value is according to the actual subject. Lines of the device list are restricted by the quantity of ibox"
            ::= { hwSiteIboxEntry 1 }

        hwIboxEquipId OBJECT-TYPE
            SYNTAX Unsigned32 (29001..29255)
            MAX-ACCESS read-only
            STATUS current
            DESCRIPTION
                "ibox device ID. Value range: 029'001 to 029'255, in which the first digits indicate the device type and the last three digits indicate the device SN."
            ::= { hwSiteIboxEntry 2 }

        hwIboxEquipName OBJECT-TYPE
            SYNTAX OCTET STRING (SIZE (0..63))
            MAX-ACCESS read-only
            STATUS current
            DESCRIPTION
                "Ibox name, of the character string type, is used to specify battery cabinet. Users can configure it.
                Otherwise, the configured character can not be any other languages except English.
                "
            ::= { hwSiteIboxEntry 3 }

        hwIbatEquipNum OBJECT-TYPE
            SYNTAX Unsigned32 (0..96)
            MAX-ACCESS read-write
            STATUS current
            DESCRIPTION
                "Number of Batteries.
                Value range: 0 to 96,
                and the value is an integer (1).
                If the value is 2147483647(0x7FFFFFFF), it indicates that the value is invalid.
                 
                "
            ::= { hwSiteIboxEntry 4 }

        hwSiteIbat OBJECT IDENTIFIER ::= { hwSiteMonitorMIBObjects 21 }

        hwSiteIbatTable OBJECT-TYPE
            SYNTAX SEQUENCE OF HwSiteIbatEntry
            MAX-ACCESS not-accessible
             STATUS current
             DESCRIPTION
                "/"
            ::= { hwSiteIbat 1 }

        hwSiteIbatEntry OBJECT-TYPE
                        SYNTAX HwSiteIbatEntry
            MAX-ACCESS not-accessible
             STATUS current
             DESCRIPTION
                "/"
            INDEX { hwIbatIndex }
            ::= { hwSiteIbatTable 1 }

        HwSiteIbatEntry            ::= SEQUENCE {
                hwIbatIndex
                    Unsigned32,
                hwIbatEquipId
                    Unsigned32,
                hwIbatEquipName
                    OCTET STRING,
                hwIbatTemperature
                    Integer32,
                hwIbatVoltage
                    Unsigned32,
                hwIbatResistance
                    Unsigned32
            }

        hwIbatIndex OBJECT-TYPE
            SYNTAX Unsigned32 (24576..26112)
            MAX-ACCESS read-only
            STATUS current
            DESCRIPTION
                "ibox table index,which value is according to the actual subject. Lines of the device list are restricted by the quantity of ibox"
            ::= { hwSiteIbatEntry 1 }

        hwIbatEquipId OBJECT-TYPE
            SYNTAX Unsigned32 (30001..31537)
            MAX-ACCESS read-only
            STATUS current
            DESCRIPTION
                "ibat device ID. Value range: 030'001 to 031'537, in which the first digits indicate the device type and the last three digits indicate the device SN."
            ::= { hwSiteIbatEntry 2 }

        hwIbatEquipName OBJECT-TYPE
            SYNTAX OCTET STRING (SIZE (0..63))
            MAX-ACCESS read-only
            STATUS current
            DESCRIPTION
                "Ibat name, of the character string type, is used to specify battery cabinet. Users can configure it.
                Otherwise, the configured character can not be any other languages except English.
                "
            ::= { hwSiteIbatEntry 3 }

        hwIbatTemperature OBJECT-TYPE
            SYNTAX Integer32 (-50..125)
            MAX-ACCESS read-only
            STATUS current
            DESCRIPTION
                "Ibat temperature. It is a ibat  parameter collected in real time. 
                Value range: -50 to +125, 
                unit: centigrade (degC), 
                and the value is an integer (1).
                If the value is 2147483647(0x7FFFFFFF), it indicates that ibox temperature sensor is not configured.
                "
            ::= { hwSiteIbatEntry 4 }

        hwIbatVoltage OBJECT-TYPE
            SYNTAX Unsigned32 (0..1000)
            MAX-ACCESS read-only
            STATUS current
            DESCRIPTION
                "Ibat Voltage of the ibat. It is an inherent attribute. 
                Value range: 0 to 100, 
                Units: V, 
                and the value is accurate to one decimal place (.1).  
                If the value is 2147483647(0x7FFFFFFF), it indicates that the value is invalid.  
                "
            ::= { hwSiteIbatEntry 5 }

        hwIbatResistance OBJECT-TYPE
            SYNTAX Unsigned32 (0..100000000)
            MAX-ACCESS read-only
            STATUS current
            DESCRIPTION
                "IbatResistance
                Value range: 0 to 1000000, 
                units:  (mohm), 
                and the value is accurate to two decimal place (.01). 
                "
            ::= { hwSiteIbatEntry 6 }

        hwSiteCommExBoard OBJECT IDENTIFIER ::= { hwSiteMonitorMIBObjects 22 }

        hwSiteCommExBoardTable OBJECT-TYPE
            SYNTAX SEQUENCE OF HwSiteCommExBoardEntry
            MAX-ACCESS not-accessible
             STATUS current
             DESCRIPTION
                "/"
            ::= { hwSiteCommExBoard 1 }

        hwSiteCommExBoardEntry OBJECT-TYPE
                        SYNTAX HwSiteCommExBoardEntry
            MAX-ACCESS not-accessible
             STATUS current
             DESCRIPTION
                "/"
            INDEX { hwCommExBoardIndex }
            ::= { hwSiteCommExBoardTable 1 }

        HwSiteCommExBoardEntry            ::= SEQUENCE {
                hwCommExBoardIndex
                    Unsigned32,
                hwCommExBoardEquipId
                    Unsigned32,
                hwCommExBoardEquipName
                    OCTET STRING
            }

        hwCommExBoardIndex OBJECT-TYPE
            SYNTAX Unsigned32 (1297..1301)
            MAX-ACCESS read-only
            STATUS current
            DESCRIPTION
                "Communication Expansion Board table index,which value is according to the actual subject. Lines of the device list are restricted by the quantity of Communication Expansion Board"
            ::= { hwSiteCommExBoardEntry 1 }

        hwCommExBoardEquipId OBJECT-TYPE
            SYNTAX Unsigned32 (32266..33049)
            MAX-ACCESS read-only
            STATUS current
            DESCRIPTION
                "Communication Expansion Board device ID. Value range: 032,256 to 033,249, in which the first digits indicate the device type and the last three digits indicate the device SN."
            ::= { hwSiteCommExBoardEntry 2 }

        hwCommExBoardEquipName OBJECT-TYPE
            SYNTAX OCTET STRING (SIZE (0..63))
            MAX-ACCESS read-only
            STATUS current
            DESCRIPTION
                "Communication Expansion Board name, of the character string type, is used to specify battery cabinet. Users can configure it.
                Otherwise, the configured character can not be any other languages except English.
                "
            ::= { hwSiteCommExBoardEntry 3 }

        hwSiteDGCommExBoard OBJECT IDENTIFIER ::= { hwSiteMonitorMIBObjects 23 }

        hwSiteDGCommExBoardTable OBJECT-TYPE
            SYNTAX SEQUENCE OF HwSiteDGCommExBoardEntry
            MAX-ACCESS not-accessible
             STATUS current
             DESCRIPTION
                "/"
            ::= { hwSiteDGCommExBoard 1 }

        hwSiteDGCommExBoardEntry OBJECT-TYPE
                        SYNTAX HwSiteDGCommExBoardEntry
            MAX-ACCESS not-accessible
             STATUS current
             DESCRIPTION
                "/"
            INDEX { hwDGCommExBoardIndex }
            ::= { hwSiteDGCommExBoardTable 1 }

        HwSiteDGCommExBoardEntry            ::= SEQUENCE {
                hwDGCommExBoardIndex
                    Unsigned32,
                hwDGCommExBoardEquipId
                    Unsigned32,
                hwDGCommExBoardEquipName
                    OCTET STRING
            }

        hwDGCommExBoardIndex OBJECT-TYPE
            SYNTAX Unsigned32 (2185)
            MAX-ACCESS read-only
            STATUS current
            DESCRIPTION
                "DG Communication Expansion Board table index,which value is according to the actual subject. Lines of the device list are restricted by the quantity of DG Communication Expansion Board"
            ::= { hwSiteDGCommExBoardEntry 1 }

        hwDGCommExBoardEquipId OBJECT-TYPE
            SYNTAX Unsigned32 (34001)
            MAX-ACCESS read-only
            STATUS current
            DESCRIPTION
                "DG Communication Expansion Board device ID. Value range: 034'001, in which the first digits indicate the device type and the last three digits indicate the device SN."
            ::= { hwSiteDGCommExBoardEntry 2 }

        hwDGCommExBoardEquipName OBJECT-TYPE
            SYNTAX OCTET STRING (SIZE (0..63))
            MAX-ACCESS read-only
            STATUS current
            DESCRIPTION
                "DG Communication Expansion Board name, of the character string type, is used to specify battery cabinet. Users can configure it.
                Otherwise, the configured character can not be any other languages except English.
                "
            ::= { hwSiteDGCommExBoardEntry 3 }

        hwAcbGroupEquip OBJECT IDENTIFIER ::= { hwSiteMonitorMIBObjects 17 }

        hwAcbGroupSampTable OBJECT-TYPE
            SYNTAX SEQUENCE OF HwAcbGroupSampEntry
            MAX-ACCESS not-accessible
             STATUS current
             DESCRIPTION
                "/"
            ::= { hwAcbGroupEquip 1 }

        hwAcbGroupSampEntry OBJECT-TYPE
                        SYNTAX HwAcbGroupSampEntry
            MAX-ACCESS not-accessible
             STATUS current
             DESCRIPTION
                "/"
            INDEX { hwAcbGroupIndex }
            ::= { hwAcbGroupSampTable 1 }

        HwAcbGroupSampEntry            ::= SEQUENCE {
                hwAcbGroupIndex
                    Unsigned32,
                hwAcbGroupEquipId
                    Unsigned32,
                hwAcbGroupEquipName
                    OCTET STRING,
                hwAcbGroupBatRunningState
                    INTEGER,
                hwAcbGroupBatVolt
                    Unsigned32,
                hwAcbGroupBatCurr
                    Integer32,
                hwAcbGroupTotalCapacity
                    Unsigned32,
                hwAcbGroupTotalRemainCapacity
                    Unsigned32,
                hwAcbGroupTemperature
                    Integer32,
                hwAcbGroupBackupTime
                    Unsigned32,
                hwAcbGroupEsmuCommNum
                    Unsigned32,
                hwAcbGroupBatSoh
                    Unsigned32,
                hwAcbGroupTotalDischargeDepth
                    Unsigned32
            }

        hwAcbGroupIndex OBJECT-TYPE
            SYNTAX Unsigned32 (0..256)
            MAX-ACCESS read-only
            STATUS current
            DESCRIPTION
                "The battery group equip Index."
            ::= { hwAcbGroupSampEntry 1 }

        hwAcbGroupEquipId OBJECT-TYPE
            SYNTAX Unsigned32
            MAX-ACCESS read-only
            STATUS current
            DESCRIPTION
                "The battery group equip ID no."
            ::= { hwAcbGroupSampEntry 2 }

        hwAcbGroupEquipName OBJECT-TYPE
            SYNTAX OCTET STRING
            MAX-ACCESS read-only
            STATUS current
            DESCRIPTION
                "The battery group equip name."
            ::= { hwAcbGroupSampEntry 3 }

        hwAcbGroupBatRunningState OBJECT-TYPE
            SYNTAX INTEGER
                {
                firstOn(1),
                powerOff(2),
                float(3),
                equal(4),
                dicharge(5),
                charge(6),
                test(7),
                unknown(255)
                }
            MAX-ACCESS read-only
            STATUS current
            DESCRIPTION
                "State of the Battery group unit running state. It is an enumeration type: 
                  If the enumeration value is 1, it indicates the Battery is first on line; 
                  If the enumeration value is 2, it indicates that Battery power off; 
                  If the enumeration value is 3, it indicates  that Battery is on float charging; 
                  If the enumeration value is 4, it indicates that Battery is on equal charging; 
                  If the enumeration value is 5, it indicates that Battery is on discharge; 
                  If the enumeration value is 6, it indicates that Battery is on charge; 
                  If the enumeration value is 7, it indicates that Battery is on test; 
                  If the enumeration value is 255,  it indicates Battery uint operation status unknown. 
                "
            ::= { hwAcbGroupSampEntry 4 }

        hwAcbGroupBatVolt OBJECT-TYPE
            SYNTAX Unsigned32 (0..1000)
            MAX-ACCESS read-only
            STATUS current
            DESCRIPTION
                "The battery volt; Value range: 0 to 100, 
                units: V. 
                and the value is accurate to one decimal place (.1).  
                If the value is 2147483647(0x7FFFFFFF), it indicates that the value is invalid."
            ::= { hwAcbGroupSampEntry 5 }

        hwAcbGroupBatCurr OBJECT-TYPE
            SYNTAX Integer32 (-40000..40000)
            MAX-ACCESS read-only
            STATUS current
            DESCRIPTION
                "The battery current; Value range: -4000 to 4000, 
                units: A. 
                and the value is accurate to one decimal place (.1).  
                If the value is 2147483647(0x7FFFFFFF), it indicates that the value is invalid."
            ::= { hwAcbGroupSampEntry 6 }

        hwAcbGroupTotalCapacity OBJECT-TYPE
            SYNTAX Unsigned32 (0..100000)
            MAX-ACCESS read-only
            STATUS current
            DESCRIPTION
                "The battery total capacity; Value range: 0 to 10000, 
                units: Ah. 
                and the value is accurate to one decimal place (.1).   
                If the value is 2147483647(0x7FFFFFFF), it indicates that the value is invalid."
            ::= { hwAcbGroupSampEntry 7 }

        hwAcbGroupTotalRemainCapacity OBJECT-TYPE
            SYNTAX Unsigned32 (0..1000)
            MAX-ACCESS read-only
            STATUS current
            DESCRIPTION
                "The battery total remain capacity; Value range:0 to 100, 
                units: %. 
                and the value is accurate to one decimal place (.1).   
                If the value is 2147483647(0x7FFFFFFF), it indicates that the value is invalid."
            ::= { hwAcbGroupSampEntry 8 }

        hwAcbGroupTemperature OBJECT-TYPE
            SYNTAX Integer32 (-500..1000)
            MAX-ACCESS read-only
            STATUS current
            DESCRIPTION
                "The battery temperature; Value range:-50 to 100, 
                units: degC. 
                and the value is accurate to one decimal place (.1).   
                If the value is 2147483647(0x7FFFFFFF), it indicates that the value is invalid."
            ::= { hwAcbGroupSampEntry 9 }

        hwAcbGroupBackupTime OBJECT-TYPE
            SYNTAX Unsigned32 (0..2560)
            MAX-ACCESS read-only
            STATUS current
            DESCRIPTION
                "The battery backup time; Value range: 0 to 256, 
                units: h.
                and the value is accurate to one decimal place (.1).   
                If the value is 2147483647(0x7FFFFFFF), it indicates that the value is invalid."
            ::= { hwAcbGroupSampEntry 11 }

        hwAcbGroupEsmuCommNum OBJECT-TYPE
            SYNTAX Unsigned32 (0..768)
            MAX-ACCESS read-only
            STATUS current
            DESCRIPTION
                "The esmu communicate number; 
                Value range: 0 to 768.   
                If the value is 2147483647(0x7FFFFFFF), it indicates that the value is invalid."
            ::= { hwAcbGroupSampEntry 12 }

        hwAcbGroupBatSoh OBJECT-TYPE
            SYNTAX Unsigned32 (0..100)
            MAX-ACCESS read-only
            STATUS current
            DESCRIPTION
                "The battery soh: 0 to 100,  
                units: %. 
                and the value is accurate to one decimal place (1).   
                If the value is 2147483647(0x7FFFFFFF), it indicates that the value is invalid."
            ::= { hwAcbGroupSampEntry 13 }

        hwAcbGroupTotalDischargeDepth OBJECT-TYPE
            SYNTAX Unsigned32 (10..1000)
            MAX-ACCESS read-only
            STATUS current
            DESCRIPTION
                "The battery total discharge depth; 
                units: %. 
                and the value is accurate to one decimal place (.1).   
                If the value is 2147483647(0x7FFFFFFF), it indicates that the value is invalid."
            ::= { hwAcbGroupSampEntry 22 }

        hwAcbGroupSetTable OBJECT-TYPE
            SYNTAX SEQUENCE OF HwAcbGroupSetEntry
            MAX-ACCESS not-accessible
             STATUS current
             DESCRIPTION
                "/"
            ::= { hwAcbGroupEquip 2 }

        hwAcbGroupSetEntry OBJECT-TYPE
                        SYNTAX HwAcbGroupSetEntry
            MAX-ACCESS not-accessible
             STATUS current
             DESCRIPTION
                "/"
            INDEX { hwAcbGroupCellNum }
            ::= { hwAcbGroupSetTable 1 }

        HwAcbGroupSetEntry            ::= SEQUENCE {
                hwAcbGroupCellNum
                    Unsigned32,
                hwAcbGroupSetTotalCapacity
                    Unsigned32,
                hwAcbGroupEqualVolt
                    Unsigned32,
                hwAcbGroupFloatVolt
                    Unsigned32,
                hwAcbGroupChargeCurrLimitThr
                    Unsigned32,
                hwAcbGroupOverCurThr
                    Unsigned32,
                hwAcbGroupHighTempThr
                    Unsigned32,
                hwAcbGroupLowTempThr
                    Integer32,
                hwAcbGroupDodToAcidBattery
                    Unsigned32,
                hwAcbGroupDefaultChargeCurrLimitThr
                    Unsigned32
            }

        hwAcbGroupCellNum OBJECT-TYPE
            SYNTAX Unsigned32 (1..32)
            MAX-ACCESS read-only
            STATUS current
            DESCRIPTION
                "Battery cell number, can be configued by users. 
                Value range: 1 to 32, 
                If the value is 2147483647(0x7FFFFFFF), it indicates that the value is invalid. 
"
            ::= { hwAcbGroupSetEntry 5 }

        hwAcbGroupSetTotalCapacity OBJECT-TYPE
            SYNTAX Unsigned32 (0..10000)
            MAX-ACCESS read-only
            STATUS current
            DESCRIPTION
                "The battery total capacity; 
                units: Ah. 
                and the value is accurate to one decimal place (.1).   
                If the value is 2147483647(0x7FFFFFFF), it indicates that the value is invalid."
            ::= { hwAcbGroupSetEntry 6 }

        hwAcbGroupEqualVolt OBJECT-TYPE
            SYNTAX Unsigned32 (420..580)
            MAX-ACCESS read-write
            STATUS current
            DESCRIPTION
                "Battery equalcharge  voltage, can be configued by users. 
                Value range: 42 to 58, 
                units: v, 
                and the value is accurate to one decimal space (.1).  
                If the value is 2147483647(0x7FFFFFFF), it indicates that the value is invalid. 
"
            ::= { hwAcbGroupSetEntry 11 }

        hwAcbGroupFloatVolt OBJECT-TYPE
            SYNTAX Unsigned32 (420..580)
            MAX-ACCESS read-write
            STATUS current
            DESCRIPTION
                "Battery floatcharge voltage, can be configued by users. 
                Value range: 42 to 58, 
                units: v, 
                and the value is accurate to one decimal space (.1).  
                If the value is 2147483647(0x7FFFFFFF), it indicates that the value is invalid. 
"
            ::= { hwAcbGroupSetEntry 12 }

        hwAcbGroupChargeCurrLimitThr OBJECT-TYPE
            SYNTAX Unsigned32 (5..200)
            MAX-ACCESS read-write
            STATUS current
            DESCRIPTION
                "Battery charge limited threhold , can be configued by users. 
                Value range: 0.05 to 2, 
                units: C10, 
                and the value is accurate to one decimal space (.01).  
                If the setting value is beyond the current support range, it will fail.
                If the value is 2147483647(0x7FFFFFFF), it indicates that the value is invalid. 
"
            ::= { hwAcbGroupSetEntry 13 }

        hwAcbGroupOverCurThr OBJECT-TYPE
            SYNTAX Unsigned32 (15..120)
            MAX-ACCESS read-write
            STATUS current
            DESCRIPTION
                "Battery over charge current limited threhold , can be configued by users. 
                Value range: 0.15 to 1.2, 
                units: C10, 
                and the value is accurate to one decimal space (.01).  
                If the value is 2147483647(0x7FFFFFFF), it indicates that the value is invalid.
"
            ::= { hwAcbGroupSetEntry 14 }

        hwAcbGroupHighTempThr OBJECT-TYPE
            SYNTAX Unsigned32 (35..70)
            MAX-ACCESS read-write
            STATUS current
            DESCRIPTION
                "Upper threshold of the environment temperature alarm, can be configured by users. 
                Value range: 35 to 70, 
                units: centigrade (°C), 
                and the value is an integer (1).  
                If the value is 2147483647(0x7FFFFFFF), it indicates that the value is invalid. 
"
            ::= { hwAcbGroupSetEntry 21 }

        hwAcbGroupLowTempThr OBJECT-TYPE
            SYNTAX Integer32 (-50..10)
            MAX-ACCESS read-write
            STATUS current
            DESCRIPTION
                "Lower threshold of the environment temperature alarm, can be configured by users. 
                Value range: -50 to 10, 
                units: centigrade (degC), 
                and the value is an integer (1).  
                If the value is 2147483647(0x7FFFFFFF), it indicates that the value is invalid. 
"
            ::= { hwAcbGroupSetEntry 22 }

        hwAcbGroupDodToAcidBattery OBJECT-TYPE
            SYNTAX Unsigned32 (0..100)
            MAX-ACCESS read-write
            STATUS current
            DESCRIPTION
                "The lithium battery discharge depth for Acid Battery running; ,units: %. "
            ::= { hwAcbGroupSetEntry 26 }

        hwAcbGroupDefaultChargeCurrLimitThr OBJECT-TYPE
            SYNTAX Unsigned32 (5..200)
            MAX-ACCESS read-write
            STATUS current
            DESCRIPTION
                "Battery default charge limited threhold , can be configued by users. 
                Value range: 0.05 to 2, 
                units: C10, 
                and the value is accurate to two decimal space (.01).  
                If the setting value is beyond the current support range, it will fail.
                If the value is 2147483647(0x7FFFFFFF), it indicates that the value is invalid. "
            ::= { hwAcbGroupSetEntry 27 }

        hwAcbEquip OBJECT IDENTIFIER ::= { hwSiteMonitorMIBObjects 18 }

        hwAcbBaseTable OBJECT-TYPE
            SYNTAX SEQUENCE OF HwAcbBaseEntry
            MAX-ACCESS not-accessible
             STATUS current
             DESCRIPTION
                "/"
            ::= { hwAcbEquip 1 }

        hwAcbBaseEntry OBJECT-TYPE
                        SYNTAX HwAcbBaseEntry
            MAX-ACCESS not-accessible
             STATUS current
             DESCRIPTION
                "/"
            INDEX { hwAcbIndex }
            ::= { hwAcbBaseTable 1 }

        HwAcbBaseEntry            ::= SEQUENCE {
                hwAcbIndex
                    Unsigned32,
                hwAcbEquipId
                    Unsigned32,
                hwAcbEquipName
                    OCTET STRING,
                hwAcbEquipAddr
                    Unsigned32,
                hwAcbSoftVar
                    OCTET STRING,
                hwAcbFatherEquipname
                    OCTET STRING
            }

        hwAcbIndex OBJECT-TYPE
            SYNTAX Unsigned32 (3668..3715  )
            MAX-ACCESS read-only
            STATUS current
            DESCRIPTION
                "The battery equip Index.Value range: 3668..3715  "
            ::= { hwAcbBaseEntry 1 }

        hwAcbEquipId OBJECT-TYPE
            SYNTAX Unsigned32
            MAX-ACCESS read-only
            STATUS current
            DESCRIPTION
                "The battery equip ID no.Value range: 31001 to 31032.  "
            ::= { hwAcbBaseEntry 2 }

        hwAcbEquipName OBJECT-TYPE
            SYNTAX OCTET STRING (SIZE (0..63))
            MAX-ACCESS read-only
            STATUS current
            DESCRIPTION
                "The battery equip name."
            ::= { hwAcbBaseEntry 3 }

        hwAcbEquipAddr OBJECT-TYPE
            SYNTAX Unsigned32 (0..255)
            MAX-ACCESS read-only
            STATUS current
            DESCRIPTION
                "The battery communica address."
            ::= { hwAcbBaseEntry 4 }

        hwAcbSoftVar OBJECT-TYPE
            SYNTAX OCTET STRING (SIZE (0..5))
            MAX-ACCESS read-only
            STATUS current
            DESCRIPTION
                "The Battery software version."
            ::= { hwAcbBaseEntry 5 }

        hwAcbFatherEquipname OBJECT-TYPE
            SYNTAX OCTET STRING
            MAX-ACCESS read-only
            STATUS current
            DESCRIPTION
                "Name of the parent device of the battery father"
            ::= { hwAcbBaseEntry 9 }

        hwAcbSampTable OBJECT-TYPE
            SYNTAX SEQUENCE OF HwAcbSampEntry
            MAX-ACCESS not-accessible
             STATUS current
             DESCRIPTION
                "/"
            ::= { hwAcbEquip 2 }

        hwAcbSampEntry OBJECT-TYPE
                        SYNTAX HwAcbSampEntry
            MAX-ACCESS not-accessible
             STATUS current
             DESCRIPTION
                "/"
            INDEX { hwAcbBatVolt }
            ::= { hwAcbSampTable 1 }

        HwAcbSampEntry            ::= SEQUENCE {
                hwAcbBatVolt
                    Unsigned32,
                hwAcbBatCurr
                    Integer32,
                hwAcbRunningStatus
                    INTEGER,
                hwAcbBatSoh
                    Integer32,
                hwAcbBatCapacity
                    Integer32,
                hwAcbBatCell1Volt
                    Unsigned32,
                hwAcbBatCell2Volt
                    Unsigned32,
                hwAcbBatCell3Volt
                    Unsigned32,
                hwAcbBatCell4Volt
                    Unsigned32,
                hwAcbBatCell5Volt
                    Unsigned32,
                hwAcbBatCell6Volt
                    Unsigned32,
                hwAcbBatCell7Volt
                    Unsigned32,
                hwAcbBatCell8Volt
                    Unsigned32,
                hwAcbBatCell9Volt
                    Unsigned32,
                hwAcbBatCell10Volt
                    Unsigned32,
                hwAcbBatCell11Volt
                    Unsigned32,
                hwAcbBatCell12Volt
                    Unsigned32,
                hwAcbBatCell13Volt
                    Unsigned32,
                hwAcbBatCell14Volt
                    Unsigned32,
                hwAcbBatCell15Volt
                    Unsigned32,
                hwAcbBatCell16Volt
                    Unsigned32,
                hwAcbBatCell17Temp
                    Integer32,
                hwAcbBatCell18Temp
                    Integer32,
                hwAcbBatCell19Temp
                    Integer32,
                hwAcbBatCell20Temp
                    Integer32,
                hwAcbBatCell21Temp
                    Integer32,
                hwAcbBatCell22Temp
                    Integer32,
                hwAcbBatCell1Temp
                    Integer32,
                hwAcbBatCell2Temp
                    Integer32,
                hwAcbBatCell3Temp
                    Integer32,
                hwAcbBatCell4Temp
                    Integer32,
                hwAcbBatCell5Temp
                    Integer32,
                hwAcbBatCell6Temp
                    Integer32,
                hwAcbBatCell7Temp
                    Integer32,
                hwAcbBatCell8Temp
                    Integer32,
                hwAcbBatCell9Temp
                    Integer32,
                hwAcbBatCell10Temp
                    Integer32,
                hwAcbBatCell11Temp
                    Integer32,
                hwAcbBatCell12Temp
                    Integer32,
                hwAcbBatCell13Temp
                    Integer32,
                hwAcbBatCell14Temp
                    Integer32,
                hwAcbBatCell15Temp
                    Integer32,
                hwAcbBatCell16Temp
                    Integer32,
                hwAcbBatCell17Volt
                    Unsigned32,
                hwAcbBatCell18Volt
                    Unsigned32,
                hwAcbBatCell19Volt
                    Unsigned32,
                hwAcbBatCell20Volt
                    Unsigned32,
                hwAcbBatCell21Volt
                    Unsigned32,
                hwAcbBatCell22Volt
                    Unsigned32
            }

        hwAcbBatVolt OBJECT-TYPE
            SYNTAX Unsigned32 (0..600)
            MAX-ACCESS read-only
            STATUS current
            DESCRIPTION
                "voltage of the battery. It indicates the real-time statistics of the battery on the site. 
                Value range: 0 to 60, 
                unit: V, 
                and the value is accurate to one decimal place (.1).  
                If the value is 2147483647(0x7FFFFFFF), it indicates that the value is invalid."
            ::= { hwAcbSampEntry 1 }

        hwAcbBatCurr OBJECT-TYPE
            SYNTAX Integer32 (-2000..2000)
            MAX-ACCESS read-only
            STATUS current
            DESCRIPTION
                "Current of the battery. It indicates the real-time statistics of the battery on the site. 
                Value range: -200 to 200, 
                unit: A, 
                and the value is accurate to one decimal place (.1).  
                If the value is 2147483647(0x7FFFFFFF), it indicates that the value is invalid."
            ::= { hwAcbSampEntry 2 }

        hwAcbRunningStatus OBJECT-TYPE
            SYNTAX INTEGER
                {
                online(0),
                offline(1),
                sleep(2),
                disconnect(3),
                charge(4),
                discharge(5),
                standby(6),
                unknown(255)
                }
            MAX-ACCESS read-only
            STATUS current
            DESCRIPTION
                "Battery charging state, indicates the charging and discharging information about the battery group. It is an enumeration type. 
                If the enumeration value is 0, it indicates a battery  in the online state. 
                If the enumeration value is 1, it indicates a battery  in the Offline state. 
                If the enumeration value is 2, it indicates a battery  in the Sleep state. 
                If the enumeration value is 3, it indicates a battery  in the disconnect state. 
                If the enumeration value is 4, it indicates a battery  in the Charge state. 
                If the enumeration value is 5, it indicates a battery  in the Discharge state. 
                If the enumeration value is 6, it indicates a battery  in the Standby state. 
                If the enumeration value is 255, it indicates a battery group in the unknown state. "
            ::= { hwAcbSampEntry 3 }

        hwAcbBatSoh OBJECT-TYPE
            SYNTAX Integer32 (0..100)
            MAX-ACCESS read-only
            STATUS current
            DESCRIPTION
                "Soh of the battery. It indicates the real-time statistics of the battery on the site. 
                Value range: 0 to 100, 
                unit: %,
                and the value is accurate to two decimal place (1).   
                If the value is 2147483647(0x7FFFFFFF), it indicates that the value is invalid."
            ::= { hwAcbSampEntry 4 }

        hwAcbBatCapacity OBJECT-TYPE
            SYNTAX Integer32 (0..100000)
            MAX-ACCESS read-only
            STATUS current
            DESCRIPTION
                "Capacity of the battery. It indicates the real-time statistics of the battery on the site. 
                Value range: 0 to 10000, 
                units: Ah, 
                and the value is accurate to one decimal place (.1).  
                If the value is 2147483647(0x7FFFFFFF), it indicates that the value is invalid."
            ::= { hwAcbSampEntry 5 }

        hwAcbBatCell1Volt OBJECT-TYPE
            SYNTAX Unsigned32 (0..50)
            MAX-ACCESS read-only
            STATUS current
            DESCRIPTION
                "Voltage of the battery cell. It indicates the real-time statistics of the battery on the site. 
                Value range: 0 to 5, 
                unit: V, 
                and the value is accurate to one decimal place (.1).  
                If the value is 2147483647(0x7FFFFFFF), it indicates that the value is invalid."
            ::= { hwAcbSampEntry 6 }

        hwAcbBatCell2Volt OBJECT-TYPE
            SYNTAX Unsigned32 (0..50)
            MAX-ACCESS read-only
            STATUS current
            DESCRIPTION
                "Voltage of the battery cell. It indicates the real-time statistics of the battery on the site. 
                Value range: 0 to 5, 
                unit: V, 
                and the value is accurate to one decimal place (.1).  
                If the value is 2147483647(0x7FFFFFFF), it indicates that the value is invalid."
            ::= { hwAcbSampEntry 7 }

        hwAcbBatCell3Volt OBJECT-TYPE
            SYNTAX Unsigned32 (0..50)
            MAX-ACCESS read-only
            STATUS current
            DESCRIPTION
                "Voltage of the battery cell. It indicates the real-time statistics of the battery on the site. 
                Value range: 0 to 5, 
                unit: V, 
                and the value is accurate to one decimal place (.1).  
                If the value is 2147483647(0x7FFFFFFF), it indicates that the value is invalid."
            ::= { hwAcbSampEntry 8 }

        hwAcbBatCell4Volt OBJECT-TYPE
            SYNTAX Unsigned32 (0..50)
            MAX-ACCESS read-only
            STATUS current
            DESCRIPTION
                "Voltage of the battery cell. It indicates the real-time statistics of the battery on the site. 
                Value range: 0 to 5, 
                unit: V, 
                and the value is accurate to one decimal place (.1).  
                If the value is 2147483647(0x7FFFFFFF), it indicates that the value is invalid."
            ::= { hwAcbSampEntry 9 }

        hwAcbBatCell5Volt OBJECT-TYPE
            SYNTAX Unsigned32 (0..50)
            MAX-ACCESS read-only
            STATUS current
            DESCRIPTION
                "Voltage of the battery cell. It indicates the real-time statistics of the battery on the site. 
                Value range: 0 to 5, 
                unit: V, 
                and the value is accurate to one decimal place (.1).  
                If the value is 2147483647(0x7FFFFFFF), it indicates that the value is invalid."
            ::= { hwAcbSampEntry 10 }

        hwAcbBatCell6Volt OBJECT-TYPE
            SYNTAX Unsigned32 (0..50)
            MAX-ACCESS read-only
            STATUS current
            DESCRIPTION
                "Voltage of the battery cell. It indicates the real-time statistics of the battery on the site. 
                Value range: 0 to 5, 
                unit: V, 
                and the value is accurate to one decimal place (.1).  
                If the value is 2147483647(0x7FFFFFFF), it indicates that the value is invalid."
            ::= { hwAcbSampEntry 11 }

        hwAcbBatCell7Volt OBJECT-TYPE
            SYNTAX Unsigned32 (0..50)
            MAX-ACCESS read-only
            STATUS current
            DESCRIPTION
                "Voltage of the battery cell. It indicates the real-time statistics of the battery on the site. 
                Value range: 0 to 5, 
                unit: V, 
                and the value is accurate to one decimal place (.1).  
                If the value is 2147483647(0x7FFFFFFF), it indicates that the value is invalid."
            ::= { hwAcbSampEntry 12 }

        hwAcbBatCell8Volt OBJECT-TYPE
            SYNTAX Unsigned32 (0..50)
            MAX-ACCESS read-only
            STATUS current
            DESCRIPTION
                "Voltage of the battery cell. It indicates the real-time statistics of the battery on the site. 
                Value range: 0 to 5, 
                unit: V, 
                and the value is accurate to one decimal place (.1).  
                If the value is 2147483647(0x7FFFFFFF), it indicates that the value is invalid."
            ::= { hwAcbSampEntry 13 }

        hwAcbBatCell9Volt OBJECT-TYPE
            SYNTAX Unsigned32 (0..50)
            MAX-ACCESS read-only
            STATUS current
            DESCRIPTION
                "Voltage of the battery cell. It indicates the real-time statistics of the battery on the site. 
                Value range: 0 to 5, 
                unit: V, 
                and the value is accurate to one decimal place (.1).  
                If the value is 2147483647(0x7FFFFFFF), it indicates that the value is invalid."
            ::= { hwAcbSampEntry 14 }

        hwAcbBatCell10Volt OBJECT-TYPE
            SYNTAX Unsigned32 (0..50)
            MAX-ACCESS read-only
            STATUS current
            DESCRIPTION
                "Voltage of the battery cell. It indicates the real-time statistics of the battery on the site. 
                Value range: 0 to 5, 
                unit: V, 
                and the value is accurate to one decimal place (.1).  
                If the value is 2147483647(0x7FFFFFFF), it indicates that the value is invalid."
            ::= { hwAcbSampEntry 15 }

        hwAcbBatCell11Volt OBJECT-TYPE
            SYNTAX Unsigned32 (0..50)
            MAX-ACCESS read-only
            STATUS current
            DESCRIPTION
                "Voltage of the battery cell. It indicates the real-time statistics of the battery on the site. 
                Value range: 0 to 5, 
                unit: V, 
                and the value is accurate to one decimal place (.1).  
                If the value is 2147483647(0x7FFFFFFF), it indicates that the value is invalid."
            ::= { hwAcbSampEntry 16 }

        hwAcbBatCell12Volt OBJECT-TYPE
            SYNTAX Unsigned32 (0..50)
            MAX-ACCESS read-only
            STATUS current
            DESCRIPTION
                "Voltage of the battery cell. It indicates the real-time statistics of the battery on the site. 
                Value range: 0 to 5, 
                unit: V, 
                and the value is accurate to one decimal place (.1).  
                If the value is 2147483647(0x7FFFFFFF), it indicates that the value is invalid."
            ::= { hwAcbSampEntry 17 }

        hwAcbBatCell13Volt OBJECT-TYPE
            SYNTAX Unsigned32 (0..50)
            MAX-ACCESS read-only
            STATUS current
            DESCRIPTION
                "Voltage of the battery cell. It indicates the real-time statistics of the battery on the site. 
                Value range: 0 to 5, 
                unit: V, 
                and the value is accurate to one decimal place (.1).  
                If the value is 2147483647(0x7FFFFFFF), it indicates that the value is invalid."
            ::= { hwAcbSampEntry 18 }

        hwAcbBatCell14Volt OBJECT-TYPE
            SYNTAX Unsigned32 (0..50)
            MAX-ACCESS read-only
            STATUS current
            DESCRIPTION
                "Voltage of the battery cell. It indicates the real-time statistics of the battery on the site. 
                Value range: 0 to 5, 
                unit: V, 
                and the value is accurate to one decimal place (.1).  
                If the value is 2147483647(0x7FFFFFFF), it indicates that the value is invalid."
            ::= { hwAcbSampEntry 19 }

        hwAcbBatCell15Volt OBJECT-TYPE
            SYNTAX Unsigned32 (0..50)
            MAX-ACCESS read-only
            STATUS current
            DESCRIPTION
                "Voltage of the battery cell. It indicates the real-time statistics of the battery on the site. 
                Value range: 0 to 5, 
                unit: V, 
                and the value is accurate to one decimal place (.1).  
                If the value is 2147483647(0x7FFFFFFF), it indicates that the value is invalid."
            ::= { hwAcbSampEntry 20 }

        hwAcbBatCell16Volt OBJECT-TYPE
            SYNTAX Unsigned32 (0..50)
            MAX-ACCESS read-only
            STATUS current
            DESCRIPTION
                "Voltage of the battery cell. It indicates the real-time statistics of the battery on the site. 
                Value range: 0 to 5, 
                unit: V, 
                and the value is accurate to one decimal place (.1).  
                If the value is 2147483647(0x7FFFFFFF), it indicates that the value is invalid."
            ::= { hwAcbSampEntry 21 }

        hwAcbBatCell17Temp OBJECT-TYPE
            SYNTAX Integer32 (-1000..1000)
            MAX-ACCESS read-only
            STATUS current
            DESCRIPTION
                "Temperature of the battery cell. It indicates the real-time statistics of the battery on the site. 
                Value range: -100 to 100, 
                units: centigrade(degC), 
                and the value is accurate to one decimal place (.1).  
                If the value is 2147483647(0x7FFFFFFF), it indicates that the value is invalid."
            ::= { hwAcbSampEntry 38 }

        hwAcbBatCell18Temp OBJECT-TYPE
            SYNTAX Integer32 (-1000..1000)
            MAX-ACCESS read-only
            STATUS current
            DESCRIPTION
                "Temperature of the battery cell. It indicates the real-time statistics of the battery on the site. 
                Value range: -100 to 100, 
                units: centigrade(degC), 
                and the value is accurate to one decimal place (.1).  
                If the value is 2147483647(0x7FFFFFFF), it indicates that the value is invalid."
            ::= { hwAcbSampEntry 39 }

        hwAcbBatCell19Temp OBJECT-TYPE
            SYNTAX Integer32 (-1000..1000)
            MAX-ACCESS read-only
            STATUS current
            DESCRIPTION
                "Temperature of the battery cell. It indicates the real-time statistics of the battery on the site. 
                Value range: -100 to 100, 
                units: centigrade(degC), 
                and the value is accurate to one decimal place (.1).  
                If the value is 2147483647(0x7FFFFFFF), it indicates that the value is invalid."
            ::= { hwAcbSampEntry 40 }

        hwAcbBatCell20Temp OBJECT-TYPE
            SYNTAX Integer32 (-1000..1000)
            MAX-ACCESS read-only
            STATUS current
            DESCRIPTION
                "Temperature of the battery cell. It indicates the real-time statistics of the battery on the site. 
                Value range: -100 to 100, 
                units: centigrade(degC), 
                and the value is accurate to one decimal place (.1).  
                If the value is 2147483647(0x7FFFFFFF), it indicates that the value is invalid."
            ::= { hwAcbSampEntry 41 }

        hwAcbBatCell21Temp OBJECT-TYPE
            SYNTAX Integer32 (-1000..1000)
            MAX-ACCESS read-only
            STATUS current
            DESCRIPTION
                "Temperature of the battery cell. It indicates the real-time statistics of the battery on the site. 
                Value range: -100 to 100, 
                units: centigrade(degC), 
                and the value is accurate to one decimal place (.1).  
                If the value is 2147483647(0x7FFFFFFF), it indicates that the value is invalid."
            ::= { hwAcbSampEntry 42 }

        hwAcbBatCell22Temp OBJECT-TYPE
            SYNTAX Integer32 (-1000..1000)
            MAX-ACCESS read-only
            STATUS current
            DESCRIPTION
                "Temperature of the battery cell. It indicates the real-time statistics of the battery on the site. 
                Value range: -100 to 100, 
                units: centigrade(degC), 
                and the value is accurate to one decimal place (.1).  
                If the value is 2147483647(0x7FFFFFFF), it indicates that the value is invalid."
            ::= { hwAcbSampEntry 43 }

        hwAcbBatCell1Temp OBJECT-TYPE
            SYNTAX Integer32 (-1000..1000)
            MAX-ACCESS read-only
            STATUS current
            DESCRIPTION
                "Temperature of the battery cell. It indicates the real-time statistics of the battery on the site. 
                Value range: -100 to 100, 
                units: centigrade(degC), 
                and the value is accurate to one decimal place (.1).  
                If the value is 2147483647(0x7FFFFFFF), it indicates that the value is invalid."
            ::= { hwAcbSampEntry 22 }

        hwAcbBatCell2Temp OBJECT-TYPE
            SYNTAX Integer32 (-1000..1000)
            MAX-ACCESS read-only
            STATUS current
            DESCRIPTION
                "Temperature of the battery cell. It indicates the real-time statistics of the battery on the site. 
                Value range: -100 to 100, 
                units: centigrade(degC), 
                and the value is accurate to one decimal place (.1).  
                If the value is 2147483647(0x7FFFFFFF), it indicates that the value is invalid."
            ::= { hwAcbSampEntry 23 }

        hwAcbBatCell3Temp OBJECT-TYPE
            SYNTAX Integer32 (-1000..1000)
            MAX-ACCESS read-only
            STATUS current
            DESCRIPTION
                "Temperature of the battery cell. It indicates the real-time statistics of the battery on the site. 
                Value range: -100 to 100, 
                units: centigrade(degC), 
                and the value is accurate to one decimal place (.1).  
                If the value is 2147483647(0x7FFFFFFF), it indicates that the value is invalid."
            ::= { hwAcbSampEntry 24 }

        hwAcbBatCell4Temp OBJECT-TYPE
            SYNTAX Integer32 (-1000..1000)
            MAX-ACCESS read-only
            STATUS current
            DESCRIPTION
                "Temperature of the battery cell. It indicates the real-time statistics of the battery on the site. 
                Value range: -100 to 100, 
                units: centigrade(degC), 
                and the value is accurate to one decimal place (.1).  
                If the value is 2147483647(0x7FFFFFFF), it indicates that the value is invalid."
            ::= { hwAcbSampEntry 25 }

        hwAcbBatCell5Temp OBJECT-TYPE
            SYNTAX Integer32 (-1000..1000)
            MAX-ACCESS read-only
            STATUS current
            DESCRIPTION
                "Temperature of the battery cell. It indicates the real-time statistics of the battery on the site. 
                Value range: -100 to 100, 
                units: centigrade(degC), 
                and the value is accurate to one decimal place (.1).  
                If the value is 2147483647(0x7FFFFFFF), it indicates that the value is invalid."
            ::= { hwAcbSampEntry 26 }

        hwAcbBatCell6Temp OBJECT-TYPE
            SYNTAX Integer32 (-1000..1000)
            MAX-ACCESS read-only
            STATUS current
            DESCRIPTION
                "Temperature of the battery cell. It indicates the real-time statistics of the battery on the site. 
                Value range: -100 to 100, 
                units: centigrade(degC), 
                and the value is accurate to one decimal place (.1).  
                If the value is 2147483647(0x7FFFFFFF), it indicates that the value is invalid."
            ::= { hwAcbSampEntry 27 }

        hwAcbBatCell7Temp OBJECT-TYPE
            SYNTAX Integer32 (-1000..1000)
            MAX-ACCESS read-only
            STATUS current
            DESCRIPTION
                "Temperature of the battery cell. It indicates the real-time statistics of the battery on the site. 
                Value range: -100 to 100, 
                units: centigrade(degC), 
                and the value is accurate to one decimal place (.1).  
                If the value is 2147483647(0x7FFFFFFF), it indicates that the value is invalid."
            ::= { hwAcbSampEntry 28 }

        hwAcbBatCell8Temp OBJECT-TYPE
            SYNTAX Integer32 (-1000..1000)
            MAX-ACCESS read-only
            STATUS current
            DESCRIPTION
                "Temperature of the battery cell. It indicates the real-time statistics of the battery on the site. 
                Value range: -100 to 100, 
                units: centigrade(degC), 
                and the value is accurate to one decimal place (.1).  
                If the value is 2147483647(0x7FFFFFFF), it indicates that the value is invalid."
            ::= { hwAcbSampEntry 29 }

        hwAcbBatCell9Temp OBJECT-TYPE
            SYNTAX Integer32 (-1000..1000)
            MAX-ACCESS read-only
            STATUS current
            DESCRIPTION
                "Temperature of the battery cell. It indicates the real-time statistics of the battery on the site. 
                Value range: -100 to 100, 
                units: centigrade(degC), 
                and the value is accurate to one decimal place (.1).  
                If the value is 2147483647(0x7FFFFFFF), it indicates that the value is invalid."
            ::= { hwAcbSampEntry 30 }

        hwAcbBatCell10Temp OBJECT-TYPE
            SYNTAX Integer32 (-1000..1000)
            MAX-ACCESS read-only
            STATUS current
            DESCRIPTION
                "Temperature of the battery cell. It indicates the real-time statistics of the battery on the site. 
                Value range: -100 to 100, 
                units: centigrade(degC), 
                and the value is accurate to one decimal place (.1).  
                If the value is 2147483647(0x7FFFFFFF), it indicates that the value is invalid."
            ::= { hwAcbSampEntry 31 }

        hwAcbBatCell11Temp OBJECT-TYPE
            SYNTAX Integer32 (-1000..1000)
            MAX-ACCESS read-only
            STATUS current
            DESCRIPTION
                "Temperature of the battery cell. It indicates the real-time statistics of the battery on the site. 
                Value range: -100 to 100, 
                units: centigrade(degC), 
                and the value is accurate to one decimal place (.1).  
                If the value is 2147483647(0x7FFFFFFF), it indicates that the value is invalid."
            ::= { hwAcbSampEntry 32 }

        hwAcbBatCell12Temp OBJECT-TYPE
            SYNTAX Integer32 (-1000..1000)
            MAX-ACCESS read-only
            STATUS current
            DESCRIPTION
                "Temperature of the battery cell. It indicates the real-time statistics of the battery on the site. 
                Value range: -100 to 100, 
                units: centigrade(degC), 
                and the value is accurate to one decimal place (.1).  
                If the value is 2147483647(0x7FFFFFFF), it indicates that the value is invalid."
            ::= { hwAcbSampEntry 33 }

        hwAcbBatCell13Temp OBJECT-TYPE
            SYNTAX Integer32 (-1000..1000)
            MAX-ACCESS read-only
            STATUS current
            DESCRIPTION
                "Temperature of the battery cell. It indicates the real-time statistics of the battery on the site. 
                Value range: -100 to 100, 
                units: centigrade(degC), 
                and the value is accurate to one decimal place (.1).  
                If the value is 2147483647(0x7FFFFFFF), it indicates that the value is invalid."
            ::= { hwAcbSampEntry 34 }

        hwAcbBatCell14Temp OBJECT-TYPE
            SYNTAX Integer32 (-1000..1000)
            MAX-ACCESS read-only
            STATUS current
            DESCRIPTION
                "Temperature of the battery cell. It indicates the real-time statistics of the battery on the site. 
                Value range: -100 to 100, 
                units: centigrade(degC), 
                and the value is accurate to one decimal place (.1).  
                If the value is 2147483647(0x7FFFFFFF), it indicates that the value is invalid."
            ::= { hwAcbSampEntry 35 }

        hwAcbBatCell15Temp OBJECT-TYPE
            SYNTAX Integer32 (-1000..1000)
            MAX-ACCESS read-only
            STATUS current
            DESCRIPTION
                "Temperature of the battery cell. It indicates the real-time statistics of the battery on the site. 
                Value range: -100 to 100, 
                units: centigrade(degC), 
                and the value is accurate to one decimal place (.1).  
                If the value is 2147483647(0x7FFFFFFF), it indicates that the value is invalid."
            ::= { hwAcbSampEntry 36 }

        hwAcbBatCell16Temp OBJECT-TYPE
            SYNTAX Integer32 (-1000..1000)
            MAX-ACCESS read-only
            STATUS current
            DESCRIPTION
                "Temperature of the battery cell. It indicates the real-time statistics of the battery on the site. 
                Value range: -100 to 100, 
                units: centigrade(degC), 
                and the value is accurate to one decimal place (.1).  
                If the value is 2147483647(0x7FFFFFFF), it indicates that the value is invalid."
            ::= { hwAcbSampEntry 37 }

        hwAcbBatCell17Volt OBJECT-TYPE
            SYNTAX Unsigned32 (0..50)
            MAX-ACCESS read-only
            STATUS current
            DESCRIPTION
                "Voltage of the battery cell. It indicates the real-time statistics of the battery on the site. 
                Value range: 0 to 5, 
                unit: V, 
                and the value is accurate to one decimal place (.1).  
                If the value is 2147483647(0x7FFFFFFF), it indicates that the value is invalid."
            ::= { hwAcbSampEntry 44 }

        hwAcbBatCell18Volt OBJECT-TYPE
            SYNTAX Unsigned32 (0..50)
            MAX-ACCESS read-only
            STATUS current
            DESCRIPTION
                "Voltage of the battery cell. It indicates the real-time statistics of the battery on the site. 
                Value range: 0 to 5, 
                unit: V, 
                and the value is accurate to one decimal place (.1).  
                If the value is 2147483647(0x7FFFFFFF), it indicates that the value is invalid."
            ::= { hwAcbSampEntry 45 }

        hwAcbBatCell19Volt OBJECT-TYPE
            SYNTAX Unsigned32 (0..50)
            MAX-ACCESS read-only
            STATUS current
            DESCRIPTION
                "Voltage of the battery cell. It indicates the real-time statistics of the battery on the site. 
                Value range: 0 to 5, 
                unit: V, 
                and the value is accurate to one decimal place (.1).  
                If the value is 2147483647(0x7FFFFFFF), it indicates that the value is invalid."
            ::= { hwAcbSampEntry 46 }

        hwAcbBatCell20Volt OBJECT-TYPE
            SYNTAX Unsigned32 (0..50)
            MAX-ACCESS read-only
            STATUS current
            DESCRIPTION
                "Voltage of the battery cell. It indicates the real-time statistics of the battery on the site. 
                Value range: 0 to 5, 
                unit: V, 
                and the value is accurate to one decimal place (.1).  
                If the value is 2147483647(0x7FFFFFFF), it indicates that the value is invalid."
            ::= { hwAcbSampEntry 47 }

        hwAcbBatCell21Volt OBJECT-TYPE
            SYNTAX Unsigned32 (0..50)
            MAX-ACCESS read-only
            STATUS current
            DESCRIPTION
                "Voltage of the battery cell. It indicates the real-time statistics of the battery on the site. 
                Value range: 0 to 5, 
                unit: V, 
                and the value is accurate to one decimal place (.1).  
                If the value is 2147483647(0x7FFFFFFF), it indicates that the value is invalid."
            ::= { hwAcbSampEntry 48 }

        hwAcbBatCell22Volt OBJECT-TYPE
            SYNTAX Unsigned32 (0..50)
            MAX-ACCESS read-only
            STATUS current
            DESCRIPTION
                "Voltage of the battery cell. It indicates the real-time statistics of the battery on the site. 
                Value range: 0 to 5, 
                unit: V, 
                and the value is accurate to one decimal place (.1).  
                If the value is 2147483647(0x7FFFFFFF), it indicates that the value is invalid."
            ::= { hwAcbSampEntry 49 }

        hwAcbSetTable OBJECT-TYPE
            SYNTAX SEQUENCE OF HwAcbSetEntry
            MAX-ACCESS not-accessible
             STATUS current
             DESCRIPTION
                "/"
            ::= { hwAcbEquip 3 }

        hwAcbSetEntry OBJECT-TYPE
                        SYNTAX HwAcbSetEntry
            MAX-ACCESS not-accessible
             STATUS current
             DESCRIPTION
                "/"
            INDEX { hwAcbGyroEnable }
            ::= { hwAcbSetTable 1 }

        HwAcbSetEntry            ::= SEQUENCE {
                hwAcbGyroEnable
                    INTEGER,
                hwAcbGyroSensitivityLevel
                    INTEGER
            }

        hwAcbGyroEnable OBJECT-TYPE
            SYNTAX INTEGER
                {
                disable(0),
                enable(1),
                unknown(255)
                }
            MAX-ACCESS read-write
            STATUS current
            DESCRIPTION
                "Gyro Function Enable, 
                Restricted use in special areas. If the value of the device is within the range, but the setting fails, the function is not supported.
                It is an enumeration value: 
                If the enumeration value is 0, it means to gyro function disable,
                If the enumeration value is 1, it means to gyro function enable,
                If the enumeration value is 255, it indicates gyro in the unknown state."
            ::= { hwAcbSetEntry 5 }

        hwAcbGyroSensitivityLevel OBJECT-TYPE
            SYNTAX INTEGER
                {
                low(0),
                midium(1),
                high(2),
                unknown(255)
                }
            MAX-ACCESS read-write
            STATUS current
            DESCRIPTION
                "Gyro Level of Sensitivity.
                Restricted use in special areas. If the value of the device is within the range, but the setting fails, the function is not supported.
                It is an enumeration value:
                If the enumeration value is 0, it means to low sensitivity,
                If the enumeration value is 1, it means to medium sensitivity,
                If the enumeration value is 2, it means to high sensitivity,
                If the enumeration value is 255, it indicates gyro in the unknown level."
            ::= { hwAcbSetEntry 6 }

        hwElockEquip OBJECT IDENTIFIER ::= { hwSiteMonitorMIBObjects 27 }

        hwElockEquipTable OBJECT-TYPE
            SYNTAX SEQUENCE OF HwElockEquipEntry
            MAX-ACCESS not-accessible
             STATUS current
             DESCRIPTION
                "/"
            ::= { hwElockEquip 1 }

        hwElockEquipEntry OBJECT-TYPE
                        SYNTAX HwElockEquipEntry
            MAX-ACCESS not-accessible
             STATUS current
             DESCRIPTION
                "/"
            INDEX { hwElockEquipIndex }
            ::= { hwElockEquipTable 1 }

        HwElockEquipEntry            ::= SEQUENCE {
                hwElockEquipIndex
                    Unsigned32,
                hwElockEquipId
                    Unsigned32,
                hwElockEquipName
                    OCTET STRING
            }

        hwElockEquipIndex OBJECT-TYPE
            SYNTAX Unsigned32
            MAX-ACCESS read-only
            STATUS current
            DESCRIPTION
                "The elock equip Index."
            ::= { hwElockEquipEntry 1 }

        hwElockEquipId OBJECT-TYPE
            SYNTAX Unsigned32
            MAX-ACCESS read-only
            STATUS current
            DESCRIPTION
                "The elock  equip ID no."
            ::= { hwElockEquipEntry 2 }

        hwElockEquipName OBJECT-TYPE
            SYNTAX OCTET STRING (SIZE (0..63))
            MAX-ACCESS read-only
            STATUS current
            DESCRIPTION
                " The elock equip name."
            ::= { hwElockEquipEntry 3 }

        hwTemHumEquip OBJECT IDENTIFIER ::= { hwSiteMonitorMIBObjects 28 }

        hwTemHumEquipTable OBJECT-TYPE
            SYNTAX SEQUENCE OF HwTemHumEquipEntry
            MAX-ACCESS not-accessible
             STATUS current
             DESCRIPTION
                "/"
            ::= { hwTemHumEquip 1 }

        hwTemHumEquipEntry OBJECT-TYPE
                        SYNTAX HwTemHumEquipEntry
            MAX-ACCESS not-accessible
             STATUS current
             DESCRIPTION
                "/"
            INDEX { hwTemHumEquipIndex }
            ::= { hwTemHumEquipTable 1 }

        HwTemHumEquipEntry            ::= SEQUENCE {
                hwTemHumEquipIndex
                    Unsigned32,
                hwTemHumEquipId
                    Unsigned32,
                hwTemHumEquipName
                    OCTET STRING,
                hwTemHumEquipAmbientTemp
                    Integer32,
                hwTemHumEquipAmbientHumidity
                    Unsigned32,
                hwSetHumTempUpperLimit
                    Integer32,
                hwSetHumTempLowerLimit
                    Integer32,
                hwSetHumidityUpperLimit
                    Integer32,
                hwSetHumidityLowerLimit
                    Integer32,
                hwTemHumEquipAddress
                    Unsigned32
            }

        hwTemHumEquipIndex OBJECT-TYPE
            SYNTAX Unsigned32
            MAX-ACCESS read-only
            STATUS current
            DESCRIPTION
                "The tem_hum equip Index."
            ::= { hwTemHumEquipEntry 1 }

        hwTemHumEquipId OBJECT-TYPE
            SYNTAX Unsigned32
            MAX-ACCESS read-only
            STATUS current
            DESCRIPTION
                "The tem_hum  equip ID no."
            ::= { hwTemHumEquipEntry 2 }

        hwTemHumEquipName OBJECT-TYPE
            SYNTAX OCTET STRING (SIZE (0..63))
            MAX-ACCESS read-only
            STATUS current
            DESCRIPTION
                " The tem_hum equip name."
            ::= { hwTemHumEquipEntry 3 }

        hwTemHumEquipAmbientTemp OBJECT-TYPE
            SYNTAX Integer32 (-20..80)
            MAX-ACCESS read-only
            STATUS current
            DESCRIPTION
                "the environment temperature. 
                units: centigrade (degC), 
                and the value is an integer (1).  "
            ::= { hwTemHumEquipEntry 4 }

        hwTemHumEquipAmbientHumidity OBJECT-TYPE
            SYNTAX Unsigned32 (0..100)
            MAX-ACCESS read-only
            STATUS current
            DESCRIPTION
                "environment temperature , 
                units: %RH, 
                and the value is an integer (1).  "
            ::= { hwTemHumEquipEntry 5 }

        hwSetHumTempUpperLimit OBJECT-TYPE
            SYNTAX Integer32 ( 25..80)
            MAX-ACCESS read-write
            STATUS current
            DESCRIPTION
                "Upper threshold of the environment temperature alarm, can be configured by users. 
                Value range: 25 to 80, 
                units: centigrade (degC), 
                and the value is an integer (1). 
                If the value is 2147483647(0x7FFFFFFF), it indicates that the value is invalid.
                NOTE: There is linkage between hwSetHumTempUpperLimit and hwSetHumTempLowerLimit"
            ::= { hwTemHumEquipEntry 6 }

        hwSetHumTempLowerLimit OBJECT-TYPE
            SYNTAX Integer32 ( -20..20)
            MAX-ACCESS read-write
            STATUS current
            DESCRIPTION
                "Lower threshold of the environment temperature alarm, can be configured by users. 
                Value range: -20 to 20, 
                units: centigrade (degC), 
                and the value is an integer (1).  
                If the value is 2147483647(0x7FFFFFFF), it indicates that the value is invalid.
                NOTE: There is linkage between hwSetHumTempUpperLimit and hwSetHumTempLowerLimit"
            ::= { hwTemHumEquipEntry 7 }

        hwSetHumidityUpperLimit OBJECT-TYPE
            SYNTAX Integer32 (0..100)
            MAX-ACCESS read-write
            STATUS current
            DESCRIPTION
                "Upper threshold of the environment humility alarm, can be configured by users. 
                Value range: 0 to 100, 
                units: %RH, 
                and the value is an integer (1).  
                If the value is 2147483647(0x7FFFFFFF), it indicates that the value is invalid."
            ::= { hwTemHumEquipEntry 8 }

        hwSetHumidityLowerLimit OBJECT-TYPE
            SYNTAX Integer32 (0..100)
            MAX-ACCESS read-write
            STATUS current
            DESCRIPTION
                "Lower threshold of the environment humility alarm, can be configured by users. 
                Value range: 0 to 100, 
                units: %RH, 
                and the value is an integer (1).  
                If the value is 2147483647(0x7FFFFFFF), it indicates that the value is invalid."
            ::= { hwTemHumEquipEntry 9 }

        hwTemHumEquipAddress OBJECT-TYPE
            SYNTAX Unsigned32 (0..255)
            MAX-ACCESS read-only
            STATUS current
            DESCRIPTION
                "Device address
                And the value is an integer (1)."
            ::= { hwTemHumEquipEntry 10 }

        hwHeaterEquip OBJECT IDENTIFIER ::= { hwSiteMonitorMIBObjects 29 }

        hwHeaterDeviceTable OBJECT-TYPE
            SYNTAX SEQUENCE OF HwHeaterDeviceEntry
            MAX-ACCESS not-accessible
             STATUS current
             DESCRIPTION
                ""
            ::= { hwHeaterEquip 1 }

        hwHeaterDeviceEntry OBJECT-TYPE
                        SYNTAX HwHeaterDeviceEntry
            MAX-ACCESS not-accessible
             STATUS current
             DESCRIPTION
                ""
            INDEX { hwHeaterDeviceIndex }
            ::= { hwHeaterDeviceTable 1 }

        HwHeaterDeviceEntry            ::= SEQUENCE {
                hwHeaterDeviceIndex
                    Unsigned32,
                hwHeaterDeviceEquipId
                    Unsigned32,
                hwHeaterDeviceEquipName
                    OCTET STRING,
                hwHeaterStartTemperature
                    Integer32,
                hwHeaterStopTemperature
                    Integer32
            }

        hwHeaterDeviceIndex OBJECT-TYPE
            SYNTAX Unsigned32
            MAX-ACCESS read-only
            STATUS current
            DESCRIPTION
                "heater device table index."
            ::= { hwHeaterDeviceEntry 1 }

        hwHeaterDeviceEquipId OBJECT-TYPE
            SYNTAX Unsigned32
            MAX-ACCESS read-only
            STATUS current
            DESCRIPTION
                "heater device equipid."
            ::= { hwHeaterDeviceEntry 2 }

        hwHeaterDeviceEquipName OBJECT-TYPE
            SYNTAX OCTET STRING (SIZE (0..63))
            MAX-ACCESS read-only
            STATUS current
            DESCRIPTION
                "heater device equipname."
            ::= { hwHeaterDeviceEntry 3 }

        hwHeaterStartTemperature OBJECT-TYPE
            SYNTAX Integer32 (-10..15)
            MAX-ACCESS read-write
            STATUS current
            DESCRIPTION
                "heater start temperature;
                Value range:-10 to 15.Unit: degC.
                and the value is an integer (1).  
                If the value is 2147483647(0x7FFFFFFF), it indicates that the value is invalid. 
                note: hwHeaterStartTemperature's set value must below hwHeaterStopTemperature's value."
            ::= { hwHeaterDeviceEntry 4 }

        hwHeaterStopTemperature OBJECT-TYPE
            SYNTAX Integer32 (5..20)
            MAX-ACCESS read-write
            STATUS current
            DESCRIPTION
                "heater stop temperature;
                Value range: 5 to 20.Unit: degC.
                and the value is an integer (1).  
                If the value is 2147483647(0x7FFFFFFF), it indicates that the value is invalid.
                note: hwHeaterStartTemperature's set value must below hwHeaterStopTemperature's value."
            ::= { hwHeaterDeviceEntry 5 }

        hwSiteDMU OBJECT IDENTIFIER ::= { hwSiteMonitorMIBObjects 31 }

        hwSiteDMUSampTable OBJECT-TYPE
            SYNTAX SEQUENCE OF HwSiteDMUSampEntry
            MAX-ACCESS not-accessible
             STATUS current
             DESCRIPTION
                ""
            ::= { hwSiteDMU 1 }

        hwSiteDMUSampEntry OBJECT-TYPE
                        SYNTAX HwSiteDMUSampEntry
            MAX-ACCESS not-accessible
             STATUS current
             DESCRIPTION
                ""
            INDEX { hwDMUIndex }
            ::= { hwSiteDMUSampTable 1 }

        HwSiteDMUSampEntry            ::= SEQUENCE {
                hwDMUIndex
                    Unsigned32,
                hwDMUEquipId
                    Unsigned32,
                hwDMUEquipName
                    OCTET STRING,
                hwDMUDCOutputVoltage
                    Unsigned32,
                hwDMULoadCurrent
                    Unsigned32,
                hwDMUTotalLoadConsumption
                    Unsigned32
            }

        hwDMUIndex OBJECT-TYPE
            SYNTAX Unsigned32 (0..256)
            MAX-ACCESS read-only
            STATUS current
            DESCRIPTION
                "DMU table index,
                which value range:1 to 256. 
                Lines of the device list are restricted by the quantity of DMU."
            ::= { hwSiteDMUSampEntry 1 }

        hwDMUEquipId OBJECT-TYPE
            SYNTAX Unsigned32 (33001..33255)
            MAX-ACCESS read-only
            STATUS current
            DESCRIPTION
                "DMU device ID. 
                Value range: 033'001 to 033'255, 
                in which the first digits indicate the device type and the last three digits indicate the device SN."
            ::= { hwSiteDMUSampEntry 2 }

        hwDMUEquipName OBJECT-TYPE
            SYNTAX OCTET STRING (SIZE (0..56))
            MAX-ACCESS read-only
            STATUS current
            DESCRIPTION
                "Device name of the DMU module, 
                character string type, is used to specify the DMU module. Otherwise, the configured character can not be any other languages except English."
            ::= { hwSiteDMUSampEntry 3 }

        hwDMUDCOutputVoltage OBJECT-TYPE
            SYNTAX Unsigned32 (0..1000)
            MAX-ACCESS read-only
            STATUS current
            DESCRIPTION
                "DC output voltage: 0 to 100, 
                units: V, 
                and the value is one decimal space (.1). If the value is 2147483647(0x7FFFFFFF), it indicates that the value is invalid."
            ::= { hwSiteDMUSampEntry 4 }

        hwDMULoadCurrent OBJECT-TYPE
            SYNTAX Unsigned32 (0..300000)
            MAX-ACCESS read-only
            STATUS current
            DESCRIPTION
                "Load current: 0 to 30000, 
                units: A, 
                and the value is one decimal space (.1). If the value is 2147483647(0x7FFFFFFF), it indicates that the value is invalid."
            ::= { hwSiteDMUSampEntry 5 }

        hwDMUTotalLoadConsumption OBJECT-TYPE
            SYNTAX Unsigned32 (0..4294967295)
            MAX-ACCESS read-only
            STATUS current
            DESCRIPTION
                "Total load consumption: 0 to 4294967295, 
                units: kWh, 
                and the value is one decimal space (.1). If the value is 2147483647(0x7FFFFFFF), it indicates that the value is invalid."
            ::= { hwSiteDMUSampEntry 6 }

        hwSiteDMUSetTable OBJECT-TYPE
            SYNTAX SEQUENCE OF HwSiteDMUSetEntry
            MAX-ACCESS not-accessible
             STATUS current
             DESCRIPTION
                ""
            ::= { hwSiteDMU 2 }

        hwSiteDMUSetEntry OBJECT-TYPE
                        SYNTAX HwSiteDMUSetEntry
            MAX-ACCESS not-accessible
             STATUS current
             DESCRIPTION
                ""
            INDEX { hwSiteDMULoad1LvdEn }
            ::= { hwSiteDMUSetTable 1 }

        HwSiteDMUSetEntry            ::= SEQUENCE {
                hwSiteDMULoad1LvdEn
                    INTEGER,
                hwSiteDMULoad1LvdMode
                    INTEGER,
                hwSiteDMULoad1LvdVoltage
                    Unsigned32,
                hwSiteDMULoad1LvdReconVoltage
                    Unsigned32,
                hwSiteDMULoad1LvdTime
                    Integer32,
                hwSiteDMULoad1LvdCapacity
                    Integer32,
                hwSiteDMULoad2LvdEn
                    INTEGER,
                hwSiteDMULoad2LvdMode
                    INTEGER,
                hwSiteDMULoad2LvdVoltage
                    Unsigned32,
                hwSiteDMULoad2LvdReconVoltage
                    Unsigned32,
                hwSiteDMULoad2LvdTime
                    Integer32,
                hwSiteDMULoad2LvdCapacity
                    Integer32
            }

        hwSiteDMULoad1LvdEn OBJECT-TYPE
            SYNTAX INTEGER
                {
                disable(1),
                enable(2)
                }
            MAX-ACCESS read-write
            STATUS current
            DESCRIPTION
                "load1 lvd enable :It is an enumeration type: 
                  If the enumeration value is 1, it means to disable the lvd control; 
                  If the enumeration value is 2, it means to enable the lvd control "
            ::= { hwSiteDMUSetEntry 1 }

        hwSiteDMULoad1LvdMode OBJECT-TYPE
            SYNTAX INTEGER
                {
                voltagemode(1),
                timemode(2)
                }
            MAX-ACCESS read-write
            STATUS current
            DESCRIPTION
                "load1 lvd mode :It is an enumeration type: 
                  If the enumeration value is 1, it means the voltage mode; 
                  If the enumeration value is 2, it means the time mode "
            ::= { hwSiteDMUSetEntry 2 }

        hwSiteDMULoad1LvdVoltage OBJECT-TYPE
            SYNTAX Unsigned32 (360..560)
            MAX-ACCESS read-write
            STATUS current
            DESCRIPTION
                "Low-voltage power-off voltage of the DMU unit can be configured by users. 
                Its value range: 36 to 56, 
                units: V, 
                and the value is accurate to one decimal space (.1).  
                If the value is 2147483647(0x7FFFFFFF), it indicates that the value is invalid."
            ::= { hwSiteDMUSetEntry 3 }

        hwSiteDMULoad1LvdReconVoltage OBJECT-TYPE
            SYNTAX Unsigned32 (370..580)
            MAX-ACCESS read-write
            STATUS current
            DESCRIPTION
                "Low-voltage power-off recover of the DMU unit can be configured by users. 
                Its value range: 37.0 to 58.0, 
                unit: V, 
                and the value is accurate to one decimal space (.1).  If the value is 2147483647(0x7FFFFFFF), it indicates that the value is invalid.
                NOTE: There is linkage between hwSiteDMULoad1LvdVoltage and hwSiteDMULoad1LvdReconVoltage"
            ::= { hwSiteDMUSetEntry 4 }

        hwSiteDMULoad1LvdTime OBJECT-TYPE
            SYNTAX Integer32 (0..6000)
            MAX-ACCESS read-write
            STATUS current
            DESCRIPTION
                "Low-voltage power-off disconnected time, It can be configured by users, and its value is an integer (1). 
                Here, if lvd mode is time mode, value range defines between 0 to 6000, 
                unit: minutes(min). 
                If the value is 2147483647(0x7FFFFFFF), it indicates that the value is invalid.
                NOTE: Only the lvd in time power off mode, this parameter can be configured successfully."
            ::= { hwSiteDMUSetEntry 5 }

        hwSiteDMULoad1LvdCapacity OBJECT-TYPE
            SYNTAX Integer32 (0..99)
            MAX-ACCESS read-write
            STATUS current
            DESCRIPTION
                "Power-off unit control the power off, when Remaining capacity percentage of the battery strings is below the calue. 
                Value range: 0 to 99, 
                unit: %, 
                and the value is accurate to one decimal place (.1).  If the value is 2147483647(0x7FFFFFFF), it indicates that the value is invalid.
                NOTE: Only the lvd in capacity power off mode, this parameter can be configured successfully."
            ::= { hwSiteDMUSetEntry 6 }

        hwSiteDMULoad2LvdEn OBJECT-TYPE
            SYNTAX INTEGER
                {
                disable(1),
                enable(2)
                }
            MAX-ACCESS read-write
            STATUS current
            DESCRIPTION
                "load1 lvd enable :It is an enumeration type: 
                If the enumeration value is 1, it means to disable the lvd control; 
                If the enumeration value is 2, it means to enable the lvd control "
            ::= { hwSiteDMUSetEntry 7 }

        hwSiteDMULoad2LvdMode OBJECT-TYPE
            SYNTAX INTEGER
                {
                voltagemode(1),
                timemode(2)
                }
            MAX-ACCESS read-write
            STATUS current
            DESCRIPTION
                "load1 lvd mode :It is an enumeration type: 
                If the enumeration value is 1, it means the voltage mode; 
                If the enumeration value is 2, it means the time mode "
            ::= { hwSiteDMUSetEntry 8 }

        hwSiteDMULoad2LvdVoltage OBJECT-TYPE
            SYNTAX Unsigned32 (360..560)
            MAX-ACCESS read-write
            STATUS current
            DESCRIPTION
                "Low-voltage power-off voltage of the DMU unit can be configured by users. 
                Its value range: 36 to 56, 
                units: V, 
                and the value is accurate to one decimal space (.1).  
                If the value is 2147483647(0x7FFFFFFF), it indicates that the value is invalid."
            ::= { hwSiteDMUSetEntry 9 }

        hwSiteDMULoad2LvdReconVoltage OBJECT-TYPE
            SYNTAX Unsigned32 (370..580)
            MAX-ACCESS read-write
            STATUS current
            DESCRIPTION
                "Low-voltage power-off recover of the DMU unit can be configured by users. 
                Its value range: 37.0 to 58.0, 
                unit: V, 
                and the value is accurate to one decimal space (.1).  If the value is 2147483647(0x7FFFFFFF), it indicates that the value is invalid.
                NOTE: There is linkage between hwSiteDMULoad2LvdVoltage and hwSiteDMULoad2LvdReconVoltage"
            ::= { hwSiteDMUSetEntry 10 }

        hwSiteDMULoad2LvdTime OBJECT-TYPE
            SYNTAX Integer32 (0..6000)
            MAX-ACCESS read-write
            STATUS current
            DESCRIPTION
                "Low-voltage power-off disconnected time, It can be configured by users, and its value is an integer (1). 
                Here, if lvd mode is time mode, value range defines between 0 to 6000, 
                unit: minutes(min). 
                If the value is 2147483647(0x7FFFFFFF), it indicates that the value is invalid.
                NOTE: Only the lvd in time power off mode, this parameter can be configured successfully."
            ::= { hwSiteDMUSetEntry 11 }

        hwSiteDMULoad2LvdCapacity OBJECT-TYPE
            SYNTAX Integer32 (0..99)
            MAX-ACCESS read-write
            STATUS current
            DESCRIPTION
                "Power-off unit control the power off, when Remaining capacity percentage of the battery strings is below the calue. 
                Value range: 0 to 99, 
                unit: %,
                and the value is accurate to one decimal place (.1).  If the value is 2147483647(0x7FFFFFFF), it indicates that the value is invalid.
                NOTE: Only the lvd in capacity power off mode, this parameter can be configured successfully."
            ::= { hwSiteDMUSetEntry 12 }

        hwSiteAts OBJECT IDENTIFIER ::= { hwSiteMonitorMIBObjects 33 }

        hwAtsSampTable OBJECT-TYPE
            SYNTAX SEQUENCE OF HwAtsSampEntry
            MAX-ACCESS not-accessible
             STATUS current
             DESCRIPTION
                ""
            ::= { hwSiteAts 1 }

        hwAtsSampEntry OBJECT-TYPE
                        SYNTAX HwAtsSampEntry
            MAX-ACCESS not-accessible
             STATUS current
             DESCRIPTION
                ""
            INDEX { hwAtsIndex }
            ::= { hwAtsSampTable 1 }

        HwAtsSampEntry            ::= SEQUENCE {
                hwAtsIndex
                    Unsigned32,
                hwAtsEquipId
                    Unsigned32,
                hwAtsEquipName
                    OCTET STRING
            }

        hwAtsIndex OBJECT-TYPE
            SYNTAX Unsigned32 (0..256)
            MAX-ACCESS read-only
            STATUS current
            DESCRIPTION
                "Table index of the running ATS modules"
            ::= { hwAtsSampEntry 1 }

        hwAtsEquipId OBJECT-TYPE
            SYNTAX Unsigned32
            MAX-ACCESS read-only
            STATUS current
            DESCRIPTION
                "ATS module ID. "
            ::= { hwAtsSampEntry 2 }

        hwAtsEquipName OBJECT-TYPE
            SYNTAX OCTET STRING (SIZE (0..56))
            MAX-ACCESS read-only
            STATUS current
            DESCRIPTION
                "Device name of the ATS module"
            ::= { hwAtsSampEntry 3 }

        hwLiBatteryCabinet OBJECT IDENTIFIER ::= { hwSiteMonitorMIBObjects 34 }

        hwLiBatteryCabinetInfoTable OBJECT-TYPE
            SYNTAX SEQUENCE OF HwLiBatteryCabinetInfoEntry
            MAX-ACCESS not-accessible
             STATUS current
             DESCRIPTION
                "/"
            ::= { hwLiBatteryCabinet 1 }

        hwLiBatteryCabinetInfoEntry OBJECT-TYPE
                        SYNTAX HwLiBatteryCabinetInfoEntry
            MAX-ACCESS not-accessible
             STATUS current
             DESCRIPTION
                "/"
            INDEX { hwLiBatteryCabinetIndex }
            ::= { hwLiBatteryCabinetInfoTable 1 }

        HwLiBatteryCabinetInfoEntry            ::= SEQUENCE {
                hwLiBatteryCabinetIndex
                    Unsigned32,
                hwLiBatteryCabinetEquipId
                    Unsigned32,
                hwLiBatteryCabinetEquipName
                    OCTET STRING,
                hwLiBatteryCabinetBatteryTotalCurrent
                    Integer32,
                hwLiBatteryCabinetBMUTotalQuantity
                    Unsigned32,
                hwLiBatteryCabinetBMUOnlineQuantity
                    Unsigned32,
                hwLiBatteryCabinetBMUOfflineQuantity
                    Unsigned32
            }

        hwLiBatteryCabinetIndex OBJECT-TYPE
            SYNTAX Unsigned32
            MAX-ACCESS read-only
            STATUS current
            DESCRIPTION
                "The Li Battery Cabinet Index."
            ::= { hwLiBatteryCabinetInfoEntry 1 }

        hwLiBatteryCabinetEquipId OBJECT-TYPE
            SYNTAX Unsigned32
            MAX-ACCESS read-only
            STATUS current
            DESCRIPTION
                "The Li Battery Cabinet equip ID no."
            ::= { hwLiBatteryCabinetInfoEntry 2 }

        hwLiBatteryCabinetEquipName OBJECT-TYPE
            SYNTAX OCTET STRING (SIZE (0..63))
            MAX-ACCESS read-only
            STATUS current
            DESCRIPTION
                "The Li Battery Cabinet equip name."
            ::= { hwLiBatteryCabinetInfoEntry 3 }

        hwLiBatteryCabinetBatteryTotalCurrent OBJECT-TYPE
            SYNTAX Integer32 ( -640000..640000)
            MAX-ACCESS read-only
            STATUS current
            DESCRIPTION
                "Li battery cabinet total current: -64000 to 64000, 
                units: A, 
                and the value is one decimal space (.1). If the value is 2147483647(0x7FFFFFFF), it indicates that the value is invalid."
            ::= { hwLiBatteryCabinetInfoEntry 4 }

        hwLiBatteryCabinetBMUTotalQuantity OBJECT-TYPE
            SYNTAX Unsigned32 (0..32)
            MAX-ACCESS read-only
            STATUS current
            DESCRIPTION
                "The Total Li battary number of the LiBattery cabinet."
            ::= { hwLiBatteryCabinetInfoEntry 5 }

        hwLiBatteryCabinetBMUOnlineQuantity OBJECT-TYPE
            SYNTAX Unsigned32 (0..32)
            MAX-ACCESS read-only
            STATUS current
            DESCRIPTION
                "The  online Li battary number of the LiBattery cabinet."
            ::= { hwLiBatteryCabinetInfoEntry 6 }

        hwLiBatteryCabinetBMUOfflineQuantity OBJECT-TYPE
            SYNTAX Unsigned32 (0..32)
            MAX-ACCESS read-only
            STATUS current
            DESCRIPTION
                "The  offline Li battary number of the LiBattery cabinet."
            ::= { hwLiBatteryCabinetInfoEntry 7 }

        hwDcCabinet OBJECT IDENTIFIER ::= { hwSiteMonitorMIBObjects 35 }

        hwDcCabinetInfoTable OBJECT-TYPE
            SYNTAX SEQUENCE OF HwDcCabinetInfoEntry
            MAX-ACCESS not-accessible
             STATUS current
             DESCRIPTION
                "/"
            ::= { hwDcCabinet 1 }

        hwDcCabinetInfoEntry OBJECT-TYPE
                        SYNTAX HwDcCabinetInfoEntry
            MAX-ACCESS not-accessible
             STATUS current
             DESCRIPTION
                "/"
            INDEX { hwDcCabinetIndex }
            ::= { hwDcCabinetInfoTable 1 }

        HwDcCabinetInfoEntry            ::= SEQUENCE {
                hwDcCabinetIndex
                    Unsigned32,
                hwDcCabinetEquipId
                    Unsigned32,
                hwDcCabinetEquipName
                    OCTET STRING,
                hwDcCabinetDcVoltage
                    Unsigned32,
                hwDcCabinetIndoorTemperature
                    Integer32,
                hwDcCabinetTotalLoadCurrent
                    Unsigned32,
                hwDcCabinetCabinetModel
                    OCTET STRING,
                hwDcCabinetBatteryCurrent
                    Integer32,
                hwDcCabinetBatteryTemperature1
                    Integer32,
                hwDcCabinetBatteryTemperature2
                    Integer32,
                hwDcCabinetBatteryTemperature3
                    Integer32,
                hwDcCabinetBatteryTemperature4
                    Integer32,
                hwDcCabinetBatteryTemperature5
                    Integer32,
                hwDcCabinetBatteryTemperature6
                    Integer32,
                hwDcCabinetBatteryTemperature7
                    Integer32,
                hwDcCabinetBatteryTemperature8
                    Integer32,
                hwDcCabinetBatteryTemperature9
                    Integer32,
                hwDcCabinetBatteryTemperature10
                    Integer32
            }

        hwDcCabinetIndex OBJECT-TYPE
            SYNTAX Unsigned32
            MAX-ACCESS read-only
            STATUS current
            DESCRIPTION
                "The Dc Cabinet Index."
            ::= { hwDcCabinetInfoEntry 1 }

        hwDcCabinetEquipId OBJECT-TYPE
            SYNTAX Unsigned32
            MAX-ACCESS read-only
            STATUS current
            DESCRIPTION
                "The Dc Cabinet equip ID no."
            ::= { hwDcCabinetInfoEntry 2 }

        hwDcCabinetEquipName OBJECT-TYPE
            SYNTAX OCTET STRING (SIZE (0..63))
            MAX-ACCESS read-only
            STATUS current
            DESCRIPTION
                "The Dc Cabinet equip name."
            ::= { hwDcCabinetInfoEntry 3 }

        hwDcCabinetDcVoltage OBJECT-TYPE
            SYNTAX Unsigned32 (0..1000)
            MAX-ACCESS read-only
            STATUS current
            DESCRIPTION
                "Bus voltage  of the Dc cabinet. 
                Its value range: 0 to 100, 
                units: V, 
                and the value is accurate to one decimal space (.1).  
                If the value is 2147483647(0x7FFFFFFF), it indicates that the value is invalid."
            ::= { hwDcCabinetInfoEntry 4 }

        hwDcCabinetIndoorTemperature OBJECT-TYPE
            SYNTAX Integer32 ( -40..80)
            MAX-ACCESS read-only
            STATUS current
            DESCRIPTION
                "The environment  temperature of Dc cabinet. It is a parameter collected in real time. 
                Value range: -40 to 80,
                unit: centigrade (degC), 
                and the value is an integer .
                If the value is 2147483647(0x7FFFFFFF), it indicates that battery temperature sensor is not configured."
            ::= { hwDcCabinetInfoEntry 5 }

        hwDcCabinetTotalLoadCurrent OBJECT-TYPE
            SYNTAX Unsigned32 (0..500000)
            MAX-ACCESS read-only
            STATUS current
            DESCRIPTION
                "Load current: 0 to 50000, 
                units: A, 
                and the value is one decimal space (.1). If the value is 2147483647(0x7FFFFFFF), it indicates that the value is invalid."
            ::= { hwDcCabinetInfoEntry 6 }

        hwDcCabinetCabinetModel OBJECT-TYPE
            SYNTAX OCTET STRING
            MAX-ACCESS read-only
            STATUS current
            DESCRIPTION
                "System type name of the Dc Cabinet."
            ::= { hwDcCabinetInfoEntry 7 }

        hwDcCabinetBatteryCurrent OBJECT-TYPE
            SYNTAX Integer32 ( -500000..500000)
            MAX-ACCESS read-only
            STATUS current
            DESCRIPTION
                "DC cabinet Batt current: -50000 to 50000, 
                units: A, 
                and the value is one decimal space (.1). If the value is 2147483647(0x7FFFFFFF), it indicates that the value is invalid."
            ::= { hwDcCabinetInfoEntry 8 }

        hwDcCabinetBatteryTemperature1 OBJECT-TYPE
            SYNTAX Integer32 ( -40..80)
            MAX-ACCESS read-only
            STATUS current
            DESCRIPTION
                "Battary temperature1. It is a battary parameter collected in real time. 
                Value range: -40 to 80, 
                unit: centigrade (degC), 
                and the value is an integer .
                If the value is 2147483647(0x7FFFFFFF), it indicates that battery temperature sensor is not configured."
            ::= { hwDcCabinetInfoEntry 9 }

        hwDcCabinetBatteryTemperature2 OBJECT-TYPE
            SYNTAX Integer32 ( -40..80)
            MAX-ACCESS read-only
            STATUS current
            DESCRIPTION
                "Battary temperature2. It is a battary parameter collected in real time. 
                Value range: -40 to 80, 
                unit: centigrade (degC), 
                and the value is an integer .
                If the value is 2147483647(0x7FFFFFFF), it indicates that battery temperature sensor is not configured."
            ::= { hwDcCabinetInfoEntry 10 }

        hwDcCabinetBatteryTemperature3 OBJECT-TYPE
            SYNTAX Integer32 ( -40..80)
            MAX-ACCESS read-only
            STATUS current
            DESCRIPTION
                "Battary temperature3. It is a battary parameter collected in real time. 
                Value range: -40 to 80, 
                unit: centigrade (degC), 
                and the value is an integer .
                If the value is 2147483647(0x7FFFFFFF), it indicates that battery temperature sensor is not configured."
            ::= { hwDcCabinetInfoEntry 11 }

        hwDcCabinetBatteryTemperature4 OBJECT-TYPE
            SYNTAX Integer32 ( -40..80)
            MAX-ACCESS read-only
            STATUS current
            DESCRIPTION
                "Battary temperature4. It is a battary parameter collected in real time. 
                Value range: -40 to 80, 
                unit: centigrade (degC), 
                and the value is an integer .
                If the value is 2147483647(0x7FFFFFFF), it indicates that battery temperature sensor is not configured."
            ::= { hwDcCabinetInfoEntry 12 }

        hwDcCabinetBatteryTemperature5 OBJECT-TYPE
            SYNTAX Integer32 ( -40..80)
            MAX-ACCESS read-only
            STATUS current
            DESCRIPTION
                "Battary temperature5. It is a battary parameter collected in real time. 
                Value range: -40 to 80, 
                unit: centigrade (degC), 
                and the value is an integer .
                If the value is 2147483647(0x7FFFFFFF), it indicates that battery temperature sensor is not configured."
            ::= { hwDcCabinetInfoEntry 13 }

        hwDcCabinetBatteryTemperature6 OBJECT-TYPE
            SYNTAX Integer32 ( -40..80)
            MAX-ACCESS read-only
            STATUS current
            DESCRIPTION
                "Battary temperature6. It is a battary parameter collected in real time. 
                Value range: -40 to 80, 
                unit: centigrade (degC), 
                and the value is an integer .
                If the value is 2147483647(0x7FFFFFFF), it indicates that battery temperature sensor is not configured."
            ::= { hwDcCabinetInfoEntry 14 }

        hwDcCabinetBatteryTemperature7 OBJECT-TYPE
            SYNTAX Integer32 ( -40..80)
            MAX-ACCESS read-only
            STATUS current
            DESCRIPTION
                "Battary7 temperature. It is a battary parameter collected in real time. 
                Value range: -40 to 80, 
                unit: centigrade (degC), 
                and the value is an integer .
                If the value is 2147483647(0x7FFFFFFF), it indicates that battery temperature sensor is not configured."
            ::= { hwDcCabinetInfoEntry 15 }

        hwDcCabinetBatteryTemperature8 OBJECT-TYPE
            SYNTAX Integer32 ( -40..80)
            MAX-ACCESS read-only
            STATUS current
            DESCRIPTION
                "Battary temperature8. It is a battary parameter collected in real time. 
                Value range: -40 to 80, 
                unit: centigrade (degC), 
                and the value is an integer .
                If the value is 2147483647(0x7FFFFFFF), it indicates that battery temperature sensor is not configured."
            ::= { hwDcCabinetInfoEntry 16 }

        hwDcCabinetBatteryTemperature9 OBJECT-TYPE
            SYNTAX Integer32 ( -40..80)
            MAX-ACCESS read-only
            STATUS current
            DESCRIPTION
                "Battary temperature9. It is a battary parameter collected in real time. 
                Value range: -40 to 80, 
                unit: centigrade (degC), 
                and the value is an integer .
                If the value is 2147483647(0x7FFFFFFF), it indicates that battery temperature sensor is not configured."
            ::= { hwDcCabinetInfoEntry 17 }

        hwDcCabinetBatteryTemperature10 OBJECT-TYPE
            SYNTAX Integer32 ( -40..80)
            MAX-ACCESS read-only
            STATUS current
            DESCRIPTION
                "Battary temperature10. It is a battary parameter collected in real time. 
                Value range: -40 to 80, 
                unit: centigrade (degC), 
                and the value is an integer .
                If the value is 2147483647(0x7FFFFFFF), it indicates that battery temperature sensor is not configured."
            ::= { hwDcCabinetInfoEntry 18 }

        hwCombinedCabinet OBJECT IDENTIFIER ::= { hwSiteMonitorMIBObjects 36 }

        hwCombinedCabinetInfoTable OBJECT-TYPE
            SYNTAX SEQUENCE OF HwCombinedCabinetInfoEntry
            MAX-ACCESS not-accessible
             STATUS current
             DESCRIPTION
                "/"
            ::= { hwCombinedCabinet 1 }

        hwCombinedCabinetInfoEntry OBJECT-TYPE
                        SYNTAX HwCombinedCabinetInfoEntry
            MAX-ACCESS not-accessible
             STATUS current
             DESCRIPTION
                "/"
            INDEX { hwCombinedCabinetIndex }
            ::= { hwCombinedCabinetInfoTable 1 }

        HwCombinedCabinetInfoEntry            ::= SEQUENCE {
                hwCombinedCabinetIndex
                    Unsigned32,
                hwCombinedCabinetEquipId
                    Unsigned32,
                hwCombinedCabinetEquipName
                    OCTET STRING,
                hwCombinedCabinetDcVoltage
                    Unsigned32,
                hwCombinedCabinetBatteryTemperature1
                    Integer32,
                hwCombinedCabinetBatteryTemperature2
                    Integer32
            }

        hwCombinedCabinetIndex OBJECT-TYPE
            SYNTAX Unsigned32
            MAX-ACCESS read-only
            STATUS current
            DESCRIPTION
                "The Combined Cabinet Index."
            ::= { hwCombinedCabinetInfoEntry 1 }

        hwCombinedCabinetEquipId OBJECT-TYPE
            SYNTAX Unsigned32
            MAX-ACCESS read-only
            STATUS current
            DESCRIPTION
                "The Combined Cabinet equip ID no."
            ::= { hwCombinedCabinetInfoEntry 2 }

        hwCombinedCabinetEquipName OBJECT-TYPE
            SYNTAX OCTET STRING (SIZE (0..63))
            MAX-ACCESS read-only
            STATUS current
            DESCRIPTION
                "The Combined Cabinet equip name."
            ::= { hwCombinedCabinetInfoEntry 3 }

        hwCombinedCabinetDcVoltage OBJECT-TYPE
            SYNTAX Unsigned32 (0..1000)
            MAX-ACCESS read-only
            STATUS current
            DESCRIPTION
                "Dc voltage  of the Combined Cabinet. 
                Its value range: 0 to 100, 
                units: V, 
                and the value is accurate to one decimal space (.1).  
                If the value is 2147483647(0x7FFFFFFF), it indicates that the value is invalid."
            ::= { hwCombinedCabinetInfoEntry 4 }

        hwCombinedCabinetBatteryTemperature1 OBJECT-TYPE
            SYNTAX Integer32 ( -300..200)
            MAX-ACCESS read-only
            STATUS current
            DESCRIPTION
                "Battary temperature1. It is a battary parameter collected in real time. 
                Value range: -300 to 200, 
                unit: centigrade (degC), 
                and the value is an integer .
                If the value is 2147483647(0x7FFFFFFF), it indicates that battery temperature sensor is not configured."
            ::= { hwCombinedCabinetInfoEntry 5 }

        hwCombinedCabinetBatteryTemperature2 OBJECT-TYPE
            SYNTAX Integer32 ( -300..200)
            MAX-ACCESS read-only
            STATUS current
            DESCRIPTION
                "Battary temperature2. It is a battary parameter collected in real time. 
                Value range: -300 to 200, 
                unit: centigrade (degC), 
                and the value is an integer .
                If the value is 2147483647(0x7FFFFFFF), it indicates that battery temperature sensor is not configured."
            ::= { hwCombinedCabinetInfoEntry 6 }

        hwRectifierCabinet OBJECT IDENTIFIER ::= { hwSiteMonitorMIBObjects 37 }

        hwRectifierCabinetInfoTable OBJECT-TYPE
            SYNTAX SEQUENCE OF HwRectifierCabinetInfoEntry
            MAX-ACCESS not-accessible
             STATUS current
             DESCRIPTION
                "/"
            ::= { hwRectifierCabinet 1 }

        hwRectifierCabinetInfoEntry OBJECT-TYPE
                        SYNTAX HwRectifierCabinetInfoEntry
            MAX-ACCESS not-accessible
             STATUS current
             DESCRIPTION
                "/"
            INDEX { hwRectifierCabinetIndex }
            ::= { hwRectifierCabinetInfoTable 1 }

        HwRectifierCabinetInfoEntry            ::= SEQUENCE {
                hwRectifierCabinetIndex
                    Unsigned32,
                hwRectifierCabinetEquipId
                    Unsigned32,
                hwRectifierCabinetEquipName
                    OCTET STRING,
                hwRectifierCabinetDcVoltage
                    Unsigned32,
                hwRectifierCabinetCabinetModel
                    OCTET STRING
            }

        hwRectifierCabinetIndex OBJECT-TYPE
            SYNTAX Unsigned32
            MAX-ACCESS read-only
            STATUS current
            DESCRIPTION
                "The Rectifier Cabinet Index."
            ::= { hwRectifierCabinetInfoEntry 1 }

        hwRectifierCabinetEquipId OBJECT-TYPE
            SYNTAX Unsigned32
            MAX-ACCESS read-only
            STATUS current
            DESCRIPTION
                "The Rectifier Cabinet equip ID no."
            ::= { hwRectifierCabinetInfoEntry 2 }

        hwRectifierCabinetEquipName OBJECT-TYPE
            SYNTAX OCTET STRING (SIZE (0..63))
            MAX-ACCESS read-only
            STATUS current
            DESCRIPTION
                "The Rectifier Cabinet equip name."
            ::= { hwRectifierCabinetInfoEntry 3 }

        hwRectifierCabinetDcVoltage OBJECT-TYPE
            SYNTAX Unsigned32 (0..1000)
            MAX-ACCESS read-only
            STATUS current
            DESCRIPTION
                "Bus voltage  of the Rectifier Cabinet. 
                Its value range: 0 to 100, 
                units: V, 
                and the value is accurate to one decimal space (.1).  
                If the value is 2147483647(0x7FFFFFFF), it indicates that the value is invalid."
            ::= { hwRectifierCabinetInfoEntry 4 }

        hwRectifierCabinetCabinetModel OBJECT-TYPE
            SYNTAX OCTET STRING
            MAX-ACCESS read-only
            STATUS current
            DESCRIPTION
                "The cabinet model of the Rectifier Cabinet."
            ::= { hwRectifierCabinetInfoEntry 5 }

        hwAcCabinet OBJECT IDENTIFIER ::= { hwSiteMonitorMIBObjects 38 }

        hwAcCabinetInfoTable OBJECT-TYPE
            SYNTAX SEQUENCE OF HwAcCabinetInfoEntry
            MAX-ACCESS not-accessible
             STATUS current
             DESCRIPTION
                "/"
            ::= { hwAcCabinet 1 }

        hwAcCabinetInfoEntry OBJECT-TYPE
                        SYNTAX HwAcCabinetInfoEntry
            MAX-ACCESS not-accessible
             STATUS current
             DESCRIPTION
                "/"
            INDEX { hwAcCabinetIndex }
            ::= { hwAcCabinetInfoTable 1 }

        HwAcCabinetInfoEntry            ::= SEQUENCE {
                hwAcCabinetIndex
                    Unsigned32,
                hwAcCabinetEquipId
                    Unsigned32,
                hwAcCabinetEquipName
                    OCTET STRING,
                hwACCabinetCabinetModel
                    OCTET STRING,
                hwACCabinetIndoorTemperature
                    Integer32,
                hwACCabinetCommunicationAddress
                    Unsigned32
            }

        hwAcCabinetIndex OBJECT-TYPE
            SYNTAX Unsigned32
            MAX-ACCESS read-only
            STATUS current
            DESCRIPTION
                "The Ac Cabinet Index."
            ::= { hwAcCabinetInfoEntry 1 }

        hwAcCabinetEquipId OBJECT-TYPE
            SYNTAX Unsigned32
            MAX-ACCESS read-only
            STATUS current
            DESCRIPTION
                "The Ac Cabinet equip ID no."
            ::= { hwAcCabinetInfoEntry 2 }

        hwAcCabinetEquipName OBJECT-TYPE
            SYNTAX OCTET STRING (SIZE (0..63))
            MAX-ACCESS read-only
            STATUS current
            DESCRIPTION
                "The Ac Cabinet equip name."
            ::= { hwAcCabinetInfoEntry 3 }

        hwACCabinetCabinetModel OBJECT-TYPE
            SYNTAX OCTET STRING
            MAX-ACCESS read-only
            STATUS current
            DESCRIPTION
                "System type name of the AC Cabinet."
            ::= { hwAcCabinetInfoEntry 4 }

        hwACCabinetIndoorTemperature OBJECT-TYPE
            SYNTAX Integer32 ( -40..80)
            MAX-ACCESS read-only
            STATUS current
            DESCRIPTION
                "The temperatrue in the AC cabinet. It is a temperature collected in real time. 
                Value range: -40 to 80, 
                unit: centigrade (degC), 
                and the value is an integer .
                If the value is 2147483647(0x7FFFFFFF), it indicates that battery temperature sensor is not configured."
            ::= { hwAcCabinetInfoEntry 5 }

        hwACCabinetCommunicationAddress OBJECT-TYPE
            SYNTAX Unsigned32 (0..8)
            MAX-ACCESS read-only
            STATUS current
            DESCRIPTION
                "The communication address of the AC cabinet."
            ::= { hwAcCabinetInfoEntry 6 }

        hwController OBJECT IDENTIFIER ::= { hwSiteMonitorMIBObjects 39 }

        hwControllerInfoTable OBJECT-TYPE
            SYNTAX SEQUENCE OF HwControllerInfoEntry
            MAX-ACCESS not-accessible
             STATUS current
             DESCRIPTION
                "/"
            ::= { hwController 1 }

        hwControllerInfoEntry OBJECT-TYPE
                        SYNTAX HwControllerInfoEntry
            MAX-ACCESS not-accessible
             STATUS current
             DESCRIPTION
                "/"
            INDEX { hwControllerIndex }
            ::= { hwControllerInfoTable 1 }

        HwControllerInfoEntry            ::= SEQUENCE {
                hwControllerIndex
                    Unsigned32,
                hwControllerEquipId
                    Unsigned32,
                hwControllerEquipName
                    OCTET STRING,
                hwControllerFatherEquipname
                    OCTET STRING,
                hwControllerBuzzerEnable
                    INTEGER
            }

        hwControllerIndex OBJECT-TYPE
            SYNTAX Unsigned32
            MAX-ACCESS read-only
            STATUS current
            DESCRIPTION
                "The Controller Index."
            ::= { hwControllerInfoEntry 1 }

        hwControllerEquipId OBJECT-TYPE
            SYNTAX Unsigned32
            MAX-ACCESS read-only
            STATUS current
            DESCRIPTION
                "The Controller equip ID no."
            ::= { hwControllerInfoEntry 2 }

        hwControllerEquipName OBJECT-TYPE
            SYNTAX OCTET STRING (SIZE (0..63))
            MAX-ACCESS read-only
            STATUS current
            DESCRIPTION
                "The Controller equip name."
            ::= { hwControllerInfoEntry 3 }

        hwControllerFatherEquipname OBJECT-TYPE
            SYNTAX OCTET STRING
            MAX-ACCESS read-only
            STATUS current
            DESCRIPTION
                "Name of the parent device of the Water Sensor"
            ::= { hwControllerInfoEntry 4 }

        hwControllerBuzzerEnable OBJECT-TYPE
            SYNTAX INTEGER
                {
                enable(1),
                disable(2),
                nullOper(255)
                }
            MAX-ACCESS read-write
            STATUS current
            DESCRIPTION
                "Buzzer enabling. It manually controls the enabling of the buzzer alarm. This node is of the enumeration type. 
                When the enumeration value is 1, it means to enable the buzzer;
                When the enumeration value is 2, it means to disable the buzzer. 
                When the enumeration value is 255, it means to nulloper the buzzer. 
                "
            ::= { hwControllerInfoEntry 5 }

        hwDeviceUim OBJECT IDENTIFIER ::= { hwSiteMonitorMIBObjects 40 }

        hwDeviceUimInfoTable OBJECT-TYPE
            SYNTAX SEQUENCE OF HwDeviceUimInfoEntry
            MAX-ACCESS not-accessible
             STATUS current
             DESCRIPTION
                "/"
            ::= { hwDeviceUim 1 }

        hwDeviceUimInfoEntry OBJECT-TYPE
                        SYNTAX HwDeviceUimInfoEntry
            MAX-ACCESS not-accessible
             STATUS current
             DESCRIPTION
                "/"
            INDEX { hwDeviceUimIndex }
            ::= { hwDeviceUimInfoTable 1 }

        HwDeviceUimInfoEntry            ::= SEQUENCE {
                hwDeviceUimIndex
                    Unsigned32,
                hwDeviceUimEquipId
                    Unsigned32,
                hwDeviceUimEquipName
                    OCTET STRING,
                hwDeviceUimFatherEquipname
                    OCTET STRING
            }

        hwDeviceUimIndex OBJECT-TYPE
            SYNTAX Unsigned32
            MAX-ACCESS read-only
            STATUS current
            DESCRIPTION
                "Table index of the UIM."
            ::= { hwDeviceUimInfoEntry 1 }

        hwDeviceUimEquipId OBJECT-TYPE
            SYNTAX Unsigned32
            MAX-ACCESS read-only
            STATUS current
            DESCRIPTION
                "Device ID of the UIM."
            ::= { hwDeviceUimInfoEntry 2 }

        hwDeviceUimEquipName OBJECT-TYPE
            SYNTAX OCTET STRING (SIZE (0..63))
            MAX-ACCESS read-only
            STATUS current
            DESCRIPTION
                "Device name of the UIM."
            ::= { hwDeviceUimInfoEntry 3 }

        hwDeviceUimFatherEquipname OBJECT-TYPE
            SYNTAX OCTET STRING
            MAX-ACCESS read-only
            STATUS current
            DESCRIPTION
                "Name of the parent device of the UIM."
            ::= { hwDeviceUimInfoEntry 4 }

        hwLocalDCPower OBJECT IDENTIFIER ::= { hwSiteMonitorMIBObjects 41 }

        hwLocalDCPowerInfoTable OBJECT-TYPE
            SYNTAX SEQUENCE OF HwLocalDCPowerInfoEntry
            MAX-ACCESS not-accessible
             STATUS current
             DESCRIPTION
                "/"
            ::= { hwLocalDCPower 1 }

        hwLocalDCPowerInfoEntry OBJECT-TYPE
                        SYNTAX HwLocalDCPowerInfoEntry
            MAX-ACCESS not-accessible
             STATUS current
             DESCRIPTION
                "/"
            INDEX { hwLocalDCPowerIndex }
            ::= { hwLocalDCPowerInfoTable 1 }

        HwLocalDCPowerInfoEntry            ::= SEQUENCE {
                hwLocalDCPowerIndex
                    Unsigned32,
                hwLocalDCPowerEquipId
                    Unsigned32,
                hwLocalDCPowerEquipName
                    OCTET STRING
            }

        hwLocalDCPowerIndex OBJECT-TYPE
            SYNTAX Unsigned32
            MAX-ACCESS read-only
            STATUS current
            DESCRIPTION
                "Table index of the Local DC Power."
            ::= { hwLocalDCPowerInfoEntry 1 }

        hwLocalDCPowerEquipId OBJECT-TYPE
            SYNTAX Unsigned32
            MAX-ACCESS read-only
            STATUS current
            DESCRIPTION
                "Device ID of the Local DC Power."
            ::= { hwLocalDCPowerInfoEntry 2 }

        hwLocalDCPowerEquipName OBJECT-TYPE
            SYNTAX OCTET STRING (SIZE (0..63))
            MAX-ACCESS read-only
            STATUS current
            DESCRIPTION
                "Device name of the Local DC Power."
            ::= { hwLocalDCPowerInfoEntry 3 }

        hwACSamplingUnit OBJECT IDENTIFIER ::= { hwSiteMonitorMIBObjects 42 }

        hwACSamplingUnitInfoTable OBJECT-TYPE
            SYNTAX SEQUENCE OF HwACSamplingUnitInfoEntry
            MAX-ACCESS not-accessible
             STATUS current
             DESCRIPTION
                "/"
            ::= { hwACSamplingUnit 1 }

        hwACSamplingUnitInfoEntry OBJECT-TYPE
                        SYNTAX HwACSamplingUnitInfoEntry
            MAX-ACCESS not-accessible
             STATUS current
             DESCRIPTION
                "/"
            INDEX { hwACSamplingUnitIndex }
            ::= { hwACSamplingUnitInfoTable 1 }

        HwACSamplingUnitInfoEntry            ::= SEQUENCE {
                hwACSamplingUnitIndex
                    Unsigned32,
                hwACSamplingUnitEquipId
                    Unsigned32,
                hwACSamplingUnitEquipName
                    OCTET STRING
            }

        hwACSamplingUnitIndex OBJECT-TYPE
            SYNTAX Unsigned32
            MAX-ACCESS read-only
            STATUS current
            DESCRIPTION
                "Table index of the AC Sampling Unit."
            ::= { hwACSamplingUnitInfoEntry 1 }

        hwACSamplingUnitEquipId OBJECT-TYPE
            SYNTAX Unsigned32
            MAX-ACCESS read-only
            STATUS current
            DESCRIPTION
                "Device ID of the AC Sampling Unit."
            ::= { hwACSamplingUnitInfoEntry 2 }

        hwACSamplingUnitEquipName OBJECT-TYPE
            SYNTAX OCTET STRING (SIZE (0..63))
            MAX-ACCESS read-only
            STATUS current
            DESCRIPTION
                "Device name of the AC Sampling Unit."
            ::= { hwACSamplingUnitInfoEntry 3 }

        hwDCSamplingUnit OBJECT IDENTIFIER ::= { hwSiteMonitorMIBObjects 43 }

        hwDCSamplingUnitInfoTable OBJECT-TYPE
            SYNTAX SEQUENCE OF HwDCSamplingUnitInfoEntry
            MAX-ACCESS not-accessible
             STATUS current
             DESCRIPTION
                "/"
            ::= { hwDCSamplingUnit 1 }

        hwDCSamplingUnitInfoEntry OBJECT-TYPE
                        SYNTAX HwDCSamplingUnitInfoEntry
            MAX-ACCESS not-accessible
             STATUS current
             DESCRIPTION
                "/"
            INDEX { hwDCSamplingUnitIndex }
            ::= { hwDCSamplingUnitInfoTable 1 }

        HwDCSamplingUnitInfoEntry            ::= SEQUENCE {
                hwDCSamplingUnitIndex
                    Unsigned32,
                hwDCSamplingUnitEquipId
                    Unsigned32,
                hwDCSamplingUnitEquipName
                    OCTET STRING
            }

        hwDCSamplingUnitIndex OBJECT-TYPE
            SYNTAX Unsigned32
            MAX-ACCESS read-only
            STATUS current
            DESCRIPTION
                "Table index of the DC Sampling Unit."
            ::= { hwDCSamplingUnitInfoEntry 1 }

        hwDCSamplingUnitEquipId OBJECT-TYPE
            SYNTAX Unsigned32
            MAX-ACCESS read-only
            STATUS current
            DESCRIPTION
                "Device ID of the DC Sampling Unit."
            ::= { hwDCSamplingUnitInfoEntry 2 }

        hwDCSamplingUnitEquipName OBJECT-TYPE
            SYNTAX OCTET STRING (SIZE (0..63))
            MAX-ACCESS read-only
            STATUS current
            DESCRIPTION
                "Device name of the DC Sampling Unit."
            ::= { hwDCSamplingUnitInfoEntry 3 }

        hwFuelTank OBJECT IDENTIFIER ::= { hwSiteMonitorMIBObjects 47 }

        hwFuelTankEquip OBJECT IDENTIFIER ::= { hwFuelTank 1 }

        hwFuelTankEquipSampTable OBJECT-TYPE
            SYNTAX SEQUENCE OF HwFuelTankEquipSampEntry
            MAX-ACCESS not-accessible
             STATUS current
             DESCRIPTION
                ""
            ::= { hwFuelTankEquip 1 }

        hwFuelTankEquipSampEntry OBJECT-TYPE
                        SYNTAX HwFuelTankEquipSampEntry
            MAX-ACCESS not-accessible
             STATUS current
             DESCRIPTION
                ""
            INDEX { hwFuelTankEquipIndex }
            ::= { hwFuelTankEquipSampTable 1 }

        HwFuelTankEquipSampEntry            ::= SEQUENCE {
                hwFuelTankEquipIndex
                    Unsigned32,
                hwFuelTankEquipId
                    Unsigned32,
                hwFuelTankEquipName
                    OCTET STRING
            }

        hwFuelTankEquipIndex OBJECT-TYPE
            SYNTAX Unsigned32
            MAX-ACCESS read-only
            STATUS current
            DESCRIPTION
                "Fuel tank device table index."
            ::= { hwFuelTankEquipSampEntry 1 }

        hwFuelTankEquipId OBJECT-TYPE
            SYNTAX Unsigned32
            MAX-ACCESS read-only
            STATUS current
            DESCRIPTION
                "Fuel tank device equipid."
            ::= { hwFuelTankEquipSampEntry 2 }

        hwFuelTankEquipName OBJECT-TYPE
            SYNTAX OCTET STRING (SIZE (0..63))
            MAX-ACCESS read-only
            STATUS current
            DESCRIPTION
                "Fuel tank device equipname."
            ::= { hwFuelTankEquipSampEntry 3 }

        hwSiteHWInverter OBJECT IDENTIFIER ::= { hwSiteMonitorMIBObjects 44 }

        hwHWInverterShelf OBJECT IDENTIFIER ::= { hwSiteHWInverter 1 }

        hwHWInverterShelfSampTable OBJECT-TYPE
            SYNTAX SEQUENCE OF HwHWInverterShelfSampEntry
            MAX-ACCESS not-accessible
             STATUS current
             DESCRIPTION
                "/"
            ::= { hwHWInverterShelf 1 }

        hwHWInverterShelfSampEntry OBJECT-TYPE
                        SYNTAX HwHWInverterShelfSampEntry
            MAX-ACCESS not-accessible
             STATUS current
             DESCRIPTION
                "/"
            INDEX { hwHWInverterShelfId }
            ::= { hwHWInverterShelfSampTable 1 }

        HwHWInverterShelfSampEntry            ::= SEQUENCE {
                hwHWInverterShelfId
                    Unsigned32,
                hwHWInverterShelfName
                    OCTET STRING,
                hwHWInverterShelfModel
                    OCTET STRING,
                hwHWInverterShelfNumber
                    Unsigned32,
                hwHWInverterShelfSerial
                    OCTET STRING,
                hwHWInverterShelfInputVoltage
                    Unsigned32,
                hwHWInverterShelfInputPower
                    Unsigned32,
                hwHWInverterShelfInputCurrent
                    Unsigned32,
                hwHWInverterShelfOutputVoltage
                    Unsigned32,
                hwHWInverterShelfOutputCurrent
                    Unsigned32,
                hwHWInverterShelfOutputACFrequency
                    Unsigned32,
                hwHWInverterShelfOutputPowerFactor
                    Integer32,
                hwHWInverterShelfOutputL1PhaseVoltage
                    Unsigned32,
                hwHWInverterShelfOutputL2PhaseVoltage
                    Unsigned32,
                hwHWInverterShelfOutputL3PhaseVoltage
                    Unsigned32,
                hwHWInverterShelfOutputL1PhaseCurrent
                    Unsigned32,
                hwHWInverterShelfOutputL2PhaseCurrent
                    Unsigned32,
                hwHWInverterShelfOutputL3PhaseCurrent
                    Unsigned32,
                hwHWInverterShelfOutputL1PhasePowerFactor
                    Integer32,
                hwHWInverterShelfOutputL2PhasePowerFactor
                    Integer32,
                hwHWInverterShelfOutputL3PhasePowerFactor
                    Integer32,
                hwHWInverterShelfActivePower
                    Unsigned32,
                hwHWInverterShelfApparentPower
                    Unsigned32,
                hwHWInverterShelfFatherEquipName
                    OCTET STRING
            }

        hwHWInverterShelfId OBJECT-TYPE
            SYNTAX Unsigned32
            MAX-ACCESS read-only
            STATUS current
            DESCRIPTION
                "Device ID of the Inverter Shelf module. "
            ::= { hwHWInverterShelfSampEntry 1 }

        hwHWInverterShelfName OBJECT-TYPE
            SYNTAX OCTET STRING (SIZE (0..63))
            MAX-ACCESS read-only
            STATUS current
            DESCRIPTION
                "Name of the Inverter Shelf module group, character string type, is used to specify the rectifier module group. 
                  Otherwise, the configured character can not be any other languages except English."
            ::= { hwHWInverterShelfSampEntry 2 }

        hwHWInverterShelfModel OBJECT-TYPE
            SYNTAX OCTET STRING (SIZE (0..63))
            MAX-ACCESS read-only
            STATUS current
            DESCRIPTION
                "Model of the Inverter Shelf. Value range: 0 to 63."
            ::= { hwHWInverterShelfSampEntry 3 }

        hwHWInverterShelfNumber OBJECT-TYPE
            SYNTAX Unsigned32 (0..60)
            MAX-ACCESS read-only
            STATUS current
            DESCRIPTION
                "Total quantity of the Inverter modules. Value range: 0 to 60. Units:pcs."
            ::= { hwHWInverterShelfSampEntry 4 }

        hwHWInverterShelfSerial OBJECT-TYPE
            SYNTAX OCTET STRING (SIZE (0..63))
            MAX-ACCESS read-only
            STATUS current
            DESCRIPTION
                "Serial of the Inverter Shelf. "
            ::= { hwHWInverterShelfSampEntry 5 }

        hwHWInverterShelfInputVoltage OBJECT-TYPE
            SYNTAX Unsigned32 (0..4000)
            MAX-ACCESS read-only
            STATUS current
            DESCRIPTION
                "Input voltage of the Inverter Shelf. It is a real-time analog parameter. Value range: 0 to 400, Units: V, the value is accurate to one decimal place (.1). If the value is 2147483647(0x7FFFFFFF), it indicates that the value is invalid."
            ::= { hwHWInverterShelfSampEntry 6 }

        hwHWInverterShelfInputPower OBJECT-TYPE
            SYNTAX Unsigned32 (0..240000)
            MAX-ACCESS read-only
            STATUS current
            DESCRIPTION
                "Input power of the Inverter Shelf. It is a real-time analog parameter. Value range: 0 to 2400, Units: kW, the value is accurate to two decimal place (.01). If the value is 2147483647(0x7FFFFFFF), it indicates that the value is invalid."
            ::= { hwHWInverterShelfSampEntry 7 }

        hwHWInverterShelfInputCurrent OBJECT-TYPE
            SYNTAX Unsigned32 (0..60000)
            MAX-ACCESS read-only
            STATUS current
            DESCRIPTION
                "Input current of the Inverter Shelf. It is a real-time analog parameter. Value range: 0 to 6000, Units: A, the value is accurate to one decimal place (.1). If the value is 2147483647(0x7FFFFFFF), it indicates that the value is invalid."
            ::= { hwHWInverterShelfSampEntry 8 }

        hwHWInverterShelfOutputVoltage OBJECT-TYPE
            SYNTAX Unsigned32 (0..3000)
            MAX-ACCESS read-only
            STATUS current
            DESCRIPTION
                "Output voltage of the Inverter Shelf. It is a real-time analog parameter. Value range: 0 to 300, Units: V, the value is accurate to one decimal place (.1). If the value is 2147483647(0x7FFFFFFF), it indicates that the value is invalid."
            ::= { hwHWInverterShelfSampEntry 9 }

        hwHWInverterShelfOutputCurrent OBJECT-TYPE
            SYNTAX Unsigned32 (0..1000)
            MAX-ACCESS read-only
            STATUS current
            DESCRIPTION
                "Output current of the Inverter Shelf. It is a real-time analog parameter. Value range: 0 to 100, Units: A, the value is accurate to one decimal place (.1). If the value is 2147483647(0x7FFFFFFF), it indicates that the value is invalid."
            ::= { hwHWInverterShelfSampEntry 10 }

        hwHWInverterShelfOutputACFrequency OBJECT-TYPE
            SYNTAX Unsigned32 (0..1000)
            MAX-ACCESS read-only
            STATUS current
            DESCRIPTION
                "AC frequency of the Inverter Shelf. It is a real-time analog parameter. Value range: 0 to 100, Units: Hz, the value is accurate to one decimal place (.1). If the value is 2147483647(0x7FFFFFFF), it indicates that the value is invalid."
            ::= { hwHWInverterShelfSampEntry 11 }

        hwHWInverterShelfOutputPowerFactor OBJECT-TYPE
            SYNTAX Integer32 (-1000..1000)
            MAX-ACCESS read-only
            STATUS current
            DESCRIPTION
                "Power factor of the Inverter Shelf. It is a real-time analog parameter. Value range: -1 to 1, Units: NA, the value is accurate to three decimal place (.001). If the value is 2147483647(0x7FFFFFFF), it indicates that the value is invalid."
            ::= { hwHWInverterShelfSampEntry 12 }

        hwHWInverterShelfOutputL1PhaseVoltage OBJECT-TYPE
            SYNTAX Unsigned32 (0..8000)
            MAX-ACCESS read-only
            STATUS current
            DESCRIPTION
                "Output L1 Phase voltage of the Inverter Shelf. It is a real-time analog parameter. Value range: 0 to 800, Units: V, the value is accurate to one decimal place (.1). If the value is 2147483647(0x7FFFFFFF), it indicates that the value is invalid."
            ::= { hwHWInverterShelfSampEntry 13 }

        hwHWInverterShelfOutputL2PhaseVoltage OBJECT-TYPE
            SYNTAX Unsigned32 (0..8000)
            MAX-ACCESS read-only
            STATUS current
            DESCRIPTION
                "Output L2 Phase voltage of the Inverter Shelf. It is a real-time analog parameter. Value range: 0 to 800, Units: V, the value is accurate to one decimal place (.1). If the value is 2147483647(0x7FFFFFFF), it indicates that the value is invalid."
            ::= { hwHWInverterShelfSampEntry 14 }

        hwHWInverterShelfOutputL3PhaseVoltage OBJECT-TYPE
            SYNTAX Unsigned32 (0..8000)
            MAX-ACCESS read-only
            STATUS current
            DESCRIPTION
                "Output L3 Phase voltage of the Inverter Shelf. It is a real-time analog parameter. Value range: 0 to 800, Units: V, the value is accurate to one decimal place (.1). If the value is 2147483647(0x7FFFFFFF), it indicates that the value is invalid."
            ::= { hwHWInverterShelfSampEntry 15 }

        hwHWInverterShelfOutputL1PhaseCurrent OBJECT-TYPE
            SYNTAX Unsigned32 (0..5000)
            MAX-ACCESS read-only
            STATUS current
            DESCRIPTION
                "Output L1 Phase current of the Inverter Shelf. It is a real-time analog parameter. Value range: 0 to 500, Units: A, the value is accurate to one decimal place (.1). If the value is 2147483647(0x7FFFFFFF), it indicates that the value is invalid."
            ::= { hwHWInverterShelfSampEntry 16 }

        hwHWInverterShelfOutputL2PhaseCurrent OBJECT-TYPE
            SYNTAX Unsigned32 (0..5000)
            MAX-ACCESS read-only
            STATUS current
            DESCRIPTION
                "Output L2 Phase current of the Inverter Shelf. It is a real-time analog parameter. Value range: 0 to 500, Units: A, the value is accurate to one decimal place (.1). If the value is 2147483647(0x7FFFFFFF), it indicates that the value is invalid."
            ::= { hwHWInverterShelfSampEntry 17 }

        hwHWInverterShelfOutputL3PhaseCurrent OBJECT-TYPE
            SYNTAX Unsigned32 (0..5000)
            MAX-ACCESS read-only
            STATUS current
            DESCRIPTION
                "Output L3 Phase current of the Inverter Shelf. It is a real-time analog parameter. Value range: 0 to 500, Units: A, the value is accurate to one decimal place (.1). If the value is 2147483647(0x7FFFFFFF), it indicates that the value is invalid."
            ::= { hwHWInverterShelfSampEntry 18 }

        hwHWInverterShelfOutputL1PhasePowerFactor OBJECT-TYPE
            SYNTAX Integer32 (-100..100)
            MAX-ACCESS read-only
            STATUS current
            DESCRIPTION
                "L1 Phase power factor of the Inverter Shelf. It is a real-time analog parameter. Value range: -1 to 1, Units: NA, the value is accurate to two decimal place (.01). If the value is 2147483647(0x7FFFFFFF), it indicates that the value is invalid."
            ::= { hwHWInverterShelfSampEntry 19 }

        hwHWInverterShelfOutputL2PhasePowerFactor OBJECT-TYPE
            SYNTAX Integer32 (-100..100)
            MAX-ACCESS read-only
            STATUS current
            DESCRIPTION
                "L2 Phase power factor of the Inverter Shelf. It is a real-time analog parameter. Value range: -1 to 1, Units: NA, the value is accurate to two decimal place (.01). If the value is 2147483647(0x7FFFFFFF), it indicates that the value is invalid."
            ::= { hwHWInverterShelfSampEntry 20 }

        hwHWInverterShelfOutputL3PhasePowerFactor OBJECT-TYPE
            SYNTAX Integer32 (-100..100)
            MAX-ACCESS read-only
            STATUS current
            DESCRIPTION
                "L3 Phase power factor of the Inverter Shelf. It is a real-time analog parameter. Value range: -1 to 1, Units: NA, the value is accurate to two decimal place (.01). If the value is 2147483647(0x7FFFFFFF), it indicates that the value is invalid."
            ::= { hwHWInverterShelfSampEntry 21 }

        hwHWInverterShelfActivePower OBJECT-TYPE
            SYNTAX Unsigned32 (0..240000)
            MAX-ACCESS read-only
            STATUS current
            DESCRIPTION
                "Active power of the Inverter Shelf. It is a real-time analog parameter. Value range: 0 to 2400, Units: kW, the value is accurate to two decimal place (.01). If the value is 2147483647(0x7FFFFFFF), it indicates that the value is invalid."
            ::= { hwHWInverterShelfSampEntry 22 }

        hwHWInverterShelfApparentPower OBJECT-TYPE
            SYNTAX Unsigned32 (0..240000)
            MAX-ACCESS read-only
            STATUS current
            DESCRIPTION
                "Apparent power of the Inverter Shelf. It is a real-time analog parameter. Value range: 0 to 2400, Units: kVA, the value is accurate to two decimal place (.01). If the value is 2147483647(0x7FFFFFFF), it indicates that the value is invalid."
            ::= { hwHWInverterShelfSampEntry 23 }

        hwHWInverterShelfFatherEquipName OBJECT-TYPE
            SYNTAX OCTET STRING (SIZE (0..63))
            MAX-ACCESS read-only
            STATUS current
            DESCRIPTION
                "Name of the parent device of the inverter shelf."
            ::= { hwHWInverterShelfSampEntry 24 }

        hwHWInverterShelfSetTable OBJECT-TYPE
            SYNTAX SEQUENCE OF HwHWInverterShelfSetEntry
            MAX-ACCESS not-accessible
             STATUS current
             DESCRIPTION
                "/"
            ::= { hwHWInverterShelf 2 }

        hwHWInverterShelfSetEntry OBJECT-TYPE
                        SYNTAX HwHWInverterShelfSetEntry
            MAX-ACCESS not-accessible
             STATUS current
             DESCRIPTION
                "/"
            INDEX { hwHWInverterShelfOutputVoltageType }
            ::= { hwHWInverterShelfSetTable 1 }

        HwHWInverterShelfSetEntry            ::= SEQUENCE {
                hwHWInverterShelfOutputVoltageType
                    INTEGER,
                hwHWInverterShelfUpperInputProtectionVoltage 
                    Integer32,
                hwHWInverterShelfLowerInputProtectionVoltage 
                    Integer32,
                hwHWInverterShelfUpperOutputProtectionVoltage 
                    Integer32,
                hwHWInverterShelfLowerOutputProtectionVoltage 
                    Integer32,
                hwHWInverterShelfOnOffControl
                    INTEGER
            }

        hwHWInverterShelfOutputVoltageType OBJECT-TYPE
            SYNTAX INTEGER
                {
                lv220(1),
                lv230(2),
                unknown(255)
                }
            MAX-ACCESS read-write
            STATUS current
            DESCRIPTION
                "Output voltage type of the Inverter Shelf module. It is an enumeration type:
                If the enumeration value is 1, it indicates 220V; 
                If the enumeration value is 2, it indicates 230V;
                If the enumeration value is 255, it indicates unkown type."
            ::= { hwHWInverterShelfSetEntry 1 }

        hwHWInverterShelfUpperInputProtectionVoltage  OBJECT-TYPE
            SYNTAX Integer32 (560..600)
            MAX-ACCESS read-write
            STATUS current
            DESCRIPTION
                "Upper input protection voltage, It can be configured by users. 
                Its value range: 56 to 60, 
                units: V, 
                and the value is accurate to one decimal space (.1).  
                If the value is 2147483647(0x7FFFFFFF), it indicates that the value is invalid."
            ::= { hwHWInverterShelfSetEntry 7 }

        hwHWInverterShelfLowerInputProtectionVoltage  OBJECT-TYPE
            SYNTAX Integer32 (410..480)
            MAX-ACCESS read-write
            STATUS current
            DESCRIPTION
                "Lower input protection voltage, It can be configured by users. 
                Its value range: 41 to 48, 
                units: V, 
                and the value is accurate to one decimal space (.1).  
                If the value is 2147483647(0x7FFFFFFF), it indicates that the value is invalid."
            ::= { hwHWInverterShelfSetEntry 8 }

        hwHWInverterShelfUpperOutputProtectionVoltage  OBJECT-TYPE
            SYNTAX Integer32 (110..135)
            MAX-ACCESS read-write
            STATUS current
            DESCRIPTION
                "Upper output protection voltage, It can be configured by users. 
                Its value range: 110 to 135, 
                units: %, 
                and its value is an integer (1).  
                If the value is 2147483647(0x7FFFFFFF), it indicates that the value is invalid."
            ::= { hwHWInverterShelfSetEntry 9 }

        hwHWInverterShelfLowerOutputProtectionVoltage  OBJECT-TYPE
            SYNTAX Integer32 (65..90)
            MAX-ACCESS read-write
            STATUS current
            DESCRIPTION
                "Lower output protection voltage, It can be configured by users. 
                Its value range: 65 to 90, 
                units: %, 
                and its value is an integer (1).  
                If the value is 2147483647(0x7FFFFFFF), it indicates that the value is invalid."
            ::= { hwHWInverterShelfSetEntry 10 }

        hwHWInverterShelfOnOffControl OBJECT-TYPE
            SYNTAX INTEGER
                {
                on(1),
                off(2),
                nulloper(255)
                }
            MAX-ACCESS read-write
            STATUS current
            DESCRIPTION
                "Power-on or power-off of the inverter shelf. It is an enumeration value:
                If the NMS notifies the SNMP agent that this node is set to 1, it indicates power-on of the inverter shelf;
                If the NMS notifies the SNMP agent that this node is set to 2, it indicates power-off of the inverter shelf.
                If the NMS notifies the SNMP agent that this node is set to 255, it indicates nullOper of the inverter shelf."
            ::= { hwHWInverterShelfSetEntry 13 }

        hwECM OBJECT IDENTIFIER ::= { hwSiteHWInverter 2 }

        hwECMSampTable OBJECT-TYPE
            SYNTAX SEQUENCE OF HwECMSampEntry
            MAX-ACCESS not-accessible
             STATUS current
             DESCRIPTION
                "/"
            ::= { hwECM 1 }

        hwECMSampEntry OBJECT-TYPE
                        SYNTAX HwECMSampEntry
            MAX-ACCESS not-accessible
             STATUS current
             DESCRIPTION
                "/"
            INDEX { hwECMSampIndex }
            ::= { hwECMSampTable 1 }

        HwECMSampEntry            ::= SEQUENCE {
                hwECMSampIndex
                    Integer32,
                hwECMEquipId
                    Unsigned32,
                hwECMEquipName
                    OCTET STRING,
                hwECMBarcode
                    OCTET STRING,
                hwECMSoftwareVersion
                    OCTET STRING,
                hwECMHardwareVersion
                    OCTET STRING,
                hwECMDeviceAddress
                    Unsigned32,
                hwECMInvertersQuantity
                    Unsigned32,
                hwECMInputDCVoltage
                    Unsigned32,
                hwECMInputDCCurrent
                    Unsigned32,
                hwECMInputDCPower
                    Unsigned32,
                hwECMOutputVoltage
                    Unsigned32,
                hwECMOutputCurrent
                    Unsigned32,
                hwECMOutputFrequency
                    Unsigned32,
                hwECMOutputActivePower
                    Unsigned32,
                hwECMOutputApparentPower
                    Unsigned32,
                hwECMOutputPowerFactor
                    Integer32,
                hwECMWorkState
                    INTEGER,
                hwECMFatherEquipName
                    OCTET STRING
            }

        hwECMSampIndex OBJECT-TYPE
            SYNTAX Integer32
            MAX-ACCESS read-only
            STATUS current
            DESCRIPTION
                "Table index of the running ECM modules."
            ::= { hwECMSampEntry 1 }

        hwECMEquipId OBJECT-TYPE
            SYNTAX Unsigned32
            MAX-ACCESS read-only
            STATUS current
            DESCRIPTION
                "ECM module ID."
            ::= { hwECMSampEntry 2 }

        hwECMEquipName OBJECT-TYPE
            SYNTAX OCTET STRING (SIZE (0..63))
            MAX-ACCESS read-only
            STATUS current
            DESCRIPTION
                "Device name of the ECM module, character string type, is used to specify the ECM module. 
                  Otherwise, the configured character can not be any other languages except English."
            ::= { hwECMSampEntry 3 }

        hwECMBarcode OBJECT-TYPE
            SYNTAX OCTET STRING (SIZE (0..63))
            MAX-ACCESS read-only
            STATUS current
            DESCRIPTION
                "Barcode of the ECM module. "
            ::= { hwECMSampEntry 4 }

        hwECMSoftwareVersion OBJECT-TYPE
            SYNTAX OCTET STRING (SIZE (0..63))
            MAX-ACCESS read-only
            STATUS current
            DESCRIPTION
                "Software version of the ECM module. "
            ::= { hwECMSampEntry 5 }

        hwECMHardwareVersion OBJECT-TYPE
            SYNTAX OCTET STRING (SIZE (0..63))
            MAX-ACCESS read-only
            STATUS current
            DESCRIPTION
                "Hardware version of the ECM module. "
            ::= { hwECMSampEntry 6 }

        hwECMDeviceAddress OBJECT-TYPE
            SYNTAX Unsigned32 (0..65535)
            MAX-ACCESS read-only
            STATUS current
            DESCRIPTION
                "Device address of the ECM module. Value range: 0 to 65535. Units:NA."
            ::= { hwECMSampEntry 7 }

        hwECMInvertersQuantity OBJECT-TYPE
            SYNTAX Unsigned32 (0..60)
            MAX-ACCESS read-only
            STATUS current
            DESCRIPTION
                "Total quantity of the ECM modules. Value range: 0 to 60. Units:pcs."
            ::= { hwECMSampEntry 8 }

        hwECMInputDCVoltage OBJECT-TYPE
            SYNTAX Unsigned32 (0..4000)
            MAX-ACCESS read-only
            STATUS current
            DESCRIPTION
                "Input voltage of the ECM module. It is a real-time analog parameter. Value range: 0 to 400, Units: V, the value is accurate to one decimal place (.1). If the value is 2147483647(0x7FFFFFFF), it indicates that the value is invalid."
            ::= { hwECMSampEntry 9 }

        hwECMInputDCCurrent OBJECT-TYPE
            SYNTAX Unsigned32 (0..10000)
            MAX-ACCESS read-only
            STATUS current
            DESCRIPTION
                "Input current of the ECM module. It is a real-time analog parameter. Value range: 0 to 1000, Units: A, the value is accurate to one decimal place (.1). If the value is 2147483647(0x7FFFFFFF), it indicates that the value is invalid."
            ::= { hwECMSampEntry 10 }

        hwECMInputDCPower OBJECT-TYPE
            SYNTAX Unsigned32 (0..40000)
            MAX-ACCESS read-only
            STATUS current
            DESCRIPTION
                "Input power of the ECM module. It is a real-time analog parameter. Value range: 0 to 400, Units: kW, the value is accurate to two decimal place (.01). If the value is 2147483647(0x7FFFFFFF), it indicates that the value is invalid."
            ::= { hwECMSampEntry 11 }

        hwECMOutputVoltage OBJECT-TYPE
            SYNTAX Unsigned32 (0..3000)
            MAX-ACCESS read-only
            STATUS current
            DESCRIPTION
                "Output voltage of the ECM module. It is a real-time analog parameter. Value range: 0 to 300, Units: V, the value is accurate to one decimal place (.1). If the value is 2147483647(0x7FFFFFFF), it indicates that the value is invalid."
            ::= { hwECMSampEntry 12 }

        hwECMOutputCurrent OBJECT-TYPE
            SYNTAX Unsigned32 (0..1000)
            MAX-ACCESS read-only
            STATUS current
            DESCRIPTION
                "Output current of the ECM module. It is a real-time analog parameter. Value range: 0 to 100, Units: A, the value is accurate to one decimal place (.1). If the value is 2147483647(0x7FFFFFFF), it indicates that the value is invalid."
            ::= { hwECMSampEntry 13 }

        hwECMOutputFrequency OBJECT-TYPE
            SYNTAX Unsigned32 (0..1000)
            MAX-ACCESS read-only
            STATUS current
            DESCRIPTION
                "AC frequency of the ECM. It is a real-time analog parameter. Value range: 0 to 100, Units: Hz, the value is accurate to one decimal place (.1). If the value is 2147483647(0x7FFFFFFF), it indicates that the value is invalid."
            ::= { hwECMSampEntry 14 }

        hwECMOutputActivePower OBJECT-TYPE
            SYNTAX Unsigned32 (0..40000)
            MAX-ACCESS read-only
            STATUS current
            DESCRIPTION
                "Active power of the ECM module. It is a real-time analog parameter. Value range: 0 to 400, Units: kW, the value is accurate to two decimal place (.01). If the value is 2147483647(0x7FFFFFFF), it indicates that the value is invalid."
            ::= { hwECMSampEntry 15 }

        hwECMOutputApparentPower OBJECT-TYPE
            SYNTAX Unsigned32 (0..40000)
            MAX-ACCESS read-only
            STATUS current
            DESCRIPTION
                "Apparent power of the ECM module. It is a real-time analog parameter. Value range: 0 to 400, Units: kVA, the value is accurate to two decimal place (.01). If the value is 2147483647(0x7FFFFFFF), it indicates that the value is invalid."
            ::= { hwECMSampEntry 16 }

        hwECMOutputPowerFactor OBJECT-TYPE
            SYNTAX Integer32 (-1000..1000)
            MAX-ACCESS read-only
            STATUS current
            DESCRIPTION
                "Power factor of the ECM module. It is a real-time analog parameter. Value range: -1 to 1, Units: NA, the value is accurate to three decimal place (.001). If the value is 2147483647(0x7FFFFFFF), it indicates that the value is invalid."
            ::= { hwECMSampEntry 17 }

        hwECMWorkState OBJECT-TYPE
            SYNTAX INTEGER
                {
                Off(1),
                NoOutput(2),
                Bypass(3),
                Inverting(4),
                unknown(255)
                }
            MAX-ACCESS read-only
            STATUS current
            DESCRIPTION
                "Work state of the ECM module. It is an enumeration type:
                If the enumeration value is 1, it indicates Off; 
                If the enumeration value is 2, it indicates No Output; 
                If the enumeration value is 3, it indicates Bypass; 
                If the enumeration value is 4, it indicates Inverting."
            ::= { hwECMSampEntry 18 }

        hwECMFatherEquipName OBJECT-TYPE
            SYNTAX OCTET STRING (SIZE (0..63))
            MAX-ACCESS read-only
            STATUS current
            DESCRIPTION
                "Name of the parent device of the ECM."
            ::= { hwECMSampEntry 19 }

        hwHWInverter OBJECT IDENTIFIER ::= { hwSiteHWInverter 3 }

        hwHWInverterModuleSampleTable OBJECT-TYPE
            SYNTAX SEQUENCE OF HwHWInverterModuleSampleEntry
            MAX-ACCESS not-accessible
             STATUS current
             DESCRIPTION
                "/"
            ::= { hwHWInverter 1 }

        hwHWInverterModuleSampleEntry OBJECT-TYPE
                        SYNTAX HwHWInverterModuleSampleEntry
            MAX-ACCESS not-accessible
             STATUS current
             DESCRIPTION
                "/"
            INDEX { hwInverterModuleSampIndex }
            ::= { hwHWInverterModuleSampleTable 1 }

        HwHWInverterModuleSampleEntry            ::= SEQUENCE {
                hwInverterModuleSampIndex
                    Integer32,
                hwInverterModuleEquipId
                    Unsigned32,
                hwInverterModuleEquipName
                    OCTET STRING,
                hwInverterModuleInputDCVoltage
                    Unsigned32,
                hwInverterModuleInputDCCurrent
                    Unsigned32,
                hwInverterModuleInputDCPower
                    Unsigned32,
                hwInverterModuleOutputVoltage
                    Unsigned32,
                hwInverterModuleOutputCurrent
                    Unsigned32,
                hwInverterModuleOutputFreqency
                    Unsigned32,
                hwInverterModuleOutputActivePower
                    Unsigned32,
                hwInverterModuleOutputApparentPower
                    Unsigned32,
                hwInverterModuleOutputPowerFactor
                    Integer32,
                hwInverterModuleFanSpeed
                    Integer32,
                hwInverterModuleTemperature
                    Integer32,
                hwInverterModuleWorkState
                    INTEGER,
                hwInverterModuleBarcode
                    OCTET STRING,
                hwInverterModuleSoftwareVersion
                    OCTET STRING,
                hwInverterModuleHardwareVersion
                    OCTET STRING,
                hwInverterModuleDeviceAddress
                    Unsigned32,
                hwInverterModuleFatherEquipName
                    OCTET STRING
            }

        hwInverterModuleSampIndex OBJECT-TYPE
            SYNTAX Integer32
            MAX-ACCESS read-only
            STATUS current
            DESCRIPTION
                "Table index of the running Inverter modules. "
            ::= { hwHWInverterModuleSampleEntry 1 }

        hwInverterModuleEquipId OBJECT-TYPE
            SYNTAX Unsigned32
            MAX-ACCESS read-only
            STATUS current
            DESCRIPTION
                "Inverter module ID. "
            ::= { hwHWInverterModuleSampleEntry 2 }

        hwInverterModuleEquipName OBJECT-TYPE
            SYNTAX OCTET STRING (SIZE (0..63))
            MAX-ACCESS read-only
            STATUS current
            DESCRIPTION
                "Device name of the Inverter module, character string type, is used to specify the Inverter module.
                  Otherwise, the configured character can not be any other languages except English."
            ::= { hwHWInverterModuleSampleEntry 3 }

        hwInverterModuleInputDCVoltage OBJECT-TYPE
            SYNTAX Unsigned32 (0..4000)
            MAX-ACCESS read-only
            STATUS current
            DESCRIPTION
                "Input voltage of the Inverter Module. It is a real-time analog parameter. Value range: 0 to 400, Units: V, the value is accurate to one decimal place (.1). If the value is 2147483647(0x7FFFFFFF), it indicates that the value is invalid."
            ::= { hwHWInverterModuleSampleEntry 4 }

        hwInverterModuleInputDCCurrent OBJECT-TYPE
            SYNTAX Unsigned32 (0..1000)
            MAX-ACCESS read-only
            STATUS current
            DESCRIPTION
                "Input current of the Inverter Module. It is a real-time analog parameter. Value range: 0 to 100, Units: A, the value is accurate to one decimal place (.1). If the value is 2147483647(0x7FFFFFFF), it indicates that the value is invalid."
            ::= { hwHWInverterModuleSampleEntry 5 }

        hwInverterModuleInputDCPower OBJECT-TYPE
            SYNTAX Unsigned32 (0..240000)
            MAX-ACCESS read-only
            STATUS current
            DESCRIPTION
                "Input power of the Inverter Module. It is a real-time analog parameter. Value range: 0 to 2400, Units: kW, the value is accurate to two decimal place (.01). If the value is 2147483647(0x7FFFFFFF), it indicates that the value is invalid."
            ::= { hwHWInverterModuleSampleEntry 6 }

        hwInverterModuleOutputVoltage OBJECT-TYPE
            SYNTAX Unsigned32 (0..3000)
            MAX-ACCESS read-only
            STATUS current
            DESCRIPTION
                "Output voltage of the Inverter Module. It is a real-time analog parameter. Value range: 0 to 300, Units: V, the value is accurate to one decimal place (.1). If the value is 2147483647(0x7FFFFFFF), it indicates that the value is invalid."
            ::= { hwHWInverterModuleSampleEntry 7 }

        hwInverterModuleOutputCurrent OBJECT-TYPE
            SYNTAX Unsigned32 (0..1000)
            MAX-ACCESS read-only
            STATUS current
            DESCRIPTION
                "Output current of the Inverter Module. It is a real-time analog parameter. Value range: 0 to 100, Units: A, the value is accurate to one decimal place (.1). If the value is 2147483647(0x7FFFFFFF), it indicates that the value is invalid."
            ::= { hwHWInverterModuleSampleEntry 8 }

        hwInverterModuleOutputFreqency OBJECT-TYPE
            SYNTAX Unsigned32 (0..1000)
            MAX-ACCESS read-only
            STATUS current
            DESCRIPTION
                "Output frequency of the Inverter Module. It is a real-time analog parameter. Value range: 0 to 100, Units: Hz, the value is accurate to one decimal place (.1). If the value is 2147483647(0x7FFFFFFF), it indicates that the value is invalid."
            ::= { hwHWInverterModuleSampleEntry 9 }

        hwInverterModuleOutputActivePower OBJECT-TYPE
            SYNTAX Unsigned32 (0..4000)
            MAX-ACCESS read-only
            STATUS current
            DESCRIPTION
                "Active power of the Inverter Module. It is a real-time analog parameter. Value range: 0 to 40, Units: kW, the value is accurate to two decimal place (.01). If the value is 2147483647(0x7FFFFFFF), it indicates that the value is invalid."
            ::= { hwHWInverterModuleSampleEntry 10 }

        hwInverterModuleOutputApparentPower OBJECT-TYPE
            SYNTAX Unsigned32 (0..4000)
            MAX-ACCESS read-only
            STATUS current
            DESCRIPTION
                "Apparent power of the Inverter Module. It is a real-time analog parameter. Value range: 0 to 40, Units: kVA, the value is accurate to two decimal place (.01). If the value is 2147483647(0x7FFFFFFF), it indicates that the value is invalid."
            ::= { hwHWInverterModuleSampleEntry 11 }

        hwInverterModuleOutputPowerFactor OBJECT-TYPE
            SYNTAX Integer32 (-1000..1000)
            MAX-ACCESS read-only
            STATUS current
            DESCRIPTION
                "Power factor of the Inverter Module. It is a real-time analog parameter. Value range: -1 to 1, Units: NA, the value is accurate to three decimal place (.001). If the value is 2147483647(0x7FFFFFFF), it indicates that the value is invalid."
            ::= { hwHWInverterModuleSampleEntry 12 }

        hwInverterModuleFanSpeed OBJECT-TYPE
            SYNTAX Integer32 (0..100)
            MAX-ACCESS read-only
            STATUS current
            DESCRIPTION
                "Fan speed control of the Inverter Module. 
                Its value range: 0 to 100, 
                units: %, 
                and its value is an integer (1).  
                If the value is 2147483647(0x7FFFFFFF), it indicates that the value is invalid."
            ::= { hwHWInverterModuleSampleEntry 13 }

        hwInverterModuleTemperature OBJECT-TYPE
            SYNTAX Integer32 (0..1000)
            MAX-ACCESS read-only
            STATUS current
            DESCRIPTION
                "Temperature of the Inverter Module. It is a real-time analog parameter. Value range: -60 to 100, Units: degC, the value is accurate to one decimal place (.1). If the value is 2147483647(0x7FFFFFFF), it indicates that the value is invalid."
            ::= { hwHWInverterModuleSampleEntry 14 }

        hwInverterModuleWorkState OBJECT-TYPE
            SYNTAX INTEGER
                {
                Off(1),
                Climbing(2),
                Selfcheck(3),
                On(4),
                unknown(255)
                }
            MAX-ACCESS read-only
            STATUS current
            DESCRIPTION
                "Work state of the Inverter module. It is an enumeration type:
                If the enumeration value is 1, it indicates Off; 
                If the enumeration value is 2, it indicates Climbing; 
                If the enumeration value is 3, it indicates Self check; 
                If the enumeration value is 4, it indicates On."
            ::= { hwHWInverterModuleSampleEntry 15 }

        hwInverterModuleBarcode OBJECT-TYPE
            SYNTAX OCTET STRING (SIZE (0..63))
            MAX-ACCESS read-only
            STATUS current
            DESCRIPTION
                "Barcode of the Inverter Module. "
            ::= { hwHWInverterModuleSampleEntry 21 }

        hwInverterModuleSoftwareVersion OBJECT-TYPE
            SYNTAX OCTET STRING (SIZE (0..63))
            MAX-ACCESS read-only
            STATUS current
            DESCRIPTION
                "Software version of the Inverter Module. "
            ::= { hwHWInverterModuleSampleEntry 22 }

        hwInverterModuleHardwareVersion OBJECT-TYPE
            SYNTAX OCTET STRING (SIZE (0..63))
            MAX-ACCESS read-only
            STATUS current
            DESCRIPTION
                "Hardware version of the Inverter Module. "
            ::= { hwHWInverterModuleSampleEntry 23 }

        hwInverterModuleDeviceAddress OBJECT-TYPE
            SYNTAX Unsigned32 (0..65535)
            MAX-ACCESS read-only
            STATUS current
            DESCRIPTION
                "Device address of the Inverter Module. Value range: 0 to 65535. Units:NA."
            ::= { hwHWInverterModuleSampleEntry 24 }

        hwInverterModuleFatherEquipName OBJECT-TYPE
            SYNTAX OCTET STRING (SIZE (0..63))
            MAX-ACCESS read-only
            STATUS current
            DESCRIPTION
                "Name of the parent device of the inverter module."
            ::= { hwHWInverterModuleSampleEntry 25 }

        hwHWInverterModuleSetTable OBJECT-TYPE
            SYNTAX SEQUENCE OF HwHWInverterModuleSetEntry
            MAX-ACCESS not-accessible
             STATUS current
             DESCRIPTION
                "/"
            ::= { hwHWInverter 2 }

        hwHWInverterModuleSetEntry OBJECT-TYPE
                        SYNTAX HwHWInverterModuleSetEntry
            MAX-ACCESS not-accessible
             STATUS current
             DESCRIPTION
                "/"
            INDEX { hwInverterModuleReset }
            ::= { hwHWInverterModuleSetTable 1 }

        HwHWInverterModuleSetEntry            ::= SEQUENCE {
                hwInverterModuleReset
                    INTEGER,
                hwInverterModuleOnOffControl
                    INTEGER
            }

        hwInverterModuleReset OBJECT-TYPE
            SYNTAX INTEGER
                {
                Reset(1)
                }
            MAX-ACCESS read-write
            STATUS current
            DESCRIPTION
                "Reset of the Invewrter module. It is an enumeration type:
                If the enumeration value is 1, it indicates reseting module."
            ::= { hwHWInverterModuleSetEntry 1 }

        hwInverterModuleOnOffControl OBJECT-TYPE
            SYNTAX INTEGER
                {
                on(1),
                off(2),
                nulloper(255)
                }
            MAX-ACCESS read-write
            STATUS current
            DESCRIPTION
                "Power-on or power-off of the inverter module. It is an enumeration value:
                If the NMS notifies the SNMP agent that this node is set to 1, it indicates power-on of the inverter module;
                If the NMS notifies the SNMP agent that this node is set to 2, it indicates power-off of the inverter module.
                If the NMS notifies the SNMP agent that this node is set to 255, it indicates nullOper of the inverter module."
            ::= { hwHWInverterModuleSetEntry 2 }

        hwPowerController OBJECT IDENTIFIER ::= { hwSiteMonitorMIBObjects 48 }

        hwPowerControllerEquip OBJECT IDENTIFIER ::= { hwPowerController 1 }

        hwPowerControllerEquipSampTable OBJECT-TYPE
            SYNTAX SEQUENCE OF HwPowerControllerEquipSampEntry
            MAX-ACCESS not-accessible
             STATUS current
             DESCRIPTION
                ""
            ::= { hwPowerControllerEquip 1 }

        hwPowerControllerEquipSampEntry OBJECT-TYPE
                        SYNTAX HwPowerControllerEquipSampEntry
            MAX-ACCESS not-accessible
             STATUS current
             DESCRIPTION
                ""
            INDEX { hwPowerControllerEquipIndex }
            ::= { hwPowerControllerEquipSampTable 1 }

        HwPowerControllerEquipSampEntry            ::= SEQUENCE {
                hwPowerControllerEquipIndex
                    Unsigned32,
                hwPowerControllerEquipId
                    Unsigned32,
                hwPowerControllerEquipName
                    OCTET STRING,
                hwPowerControllerAmbientTemp 
                    Integer32,
                hwPowerControllerACVoltage 
                    Unsigned32,
                hwPowerControllerQtyOfRect 
                    Unsigned32,
                hwPowerControllerRectifierCurrent1
                    Unsigned32,
                hwPowerControllerRectifierCurrent2
                    Unsigned32,
                hwPowerControllerRectifierCurrent3
                    Unsigned32,
                hwPowerControllerRectifierCurrent4
                    Unsigned32,
                hwPowerControllerDCVoltage 
                    Unsigned32,
                hwPowerControllerTotalLoadCurrent 
                    Integer32,
                hwPowerControllerBatteryTemperature 
                    Integer32,
                hwPowerControllerPhaseL1Volt
                    Unsigned32,
                hwPowerControllerPhaseL2Volt
                    Unsigned32,
                hwPowerControllerPhaseL3Volt
                    Unsigned32
            }

        hwPowerControllerEquipIndex OBJECT-TYPE
            SYNTAX Unsigned32
            MAX-ACCESS read-only
            STATUS current
            DESCRIPTION
                "Power Controller table index."
            ::= { hwPowerControllerEquipSampEntry 1 }

        hwPowerControllerEquipId OBJECT-TYPE
            SYNTAX Unsigned32
            MAX-ACCESS read-only
            STATUS current
            DESCRIPTION
                "Power Controller device ID. "
            ::= { hwPowerControllerEquipSampEntry 2 }

        hwPowerControllerEquipName OBJECT-TYPE
            SYNTAX OCTET STRING (SIZE (0..63))
            MAX-ACCESS read-only
            STATUS current
            DESCRIPTION
                "Power Controller name, of the character string type, is used to specify Power Controller. 
                Otherwise, the configured character can not be any other languages except English.
                "
            ::= { hwPowerControllerEquipSampEntry 3 }

        hwPowerControllerAmbientTemp  OBJECT-TYPE
            SYNTAX Integer32 ( -1000..1000)
            MAX-ACCESS read-only
            STATUS current
            DESCRIPTION
                "Power controller ambient temperature. Value range: -100 to 100, units: degC, and the value is accurate to one decimal space (.1). If the value is 2147483647(0x7FFFFFFF), it indicates that the value is invalid."
            ::= { hwPowerControllerEquipSampEntry 9 }

        hwPowerControllerACVoltage  OBJECT-TYPE
            SYNTAX Unsigned32 ( 0..4000)
            MAX-ACCESS read-only
            STATUS current
            DESCRIPTION
                "The AC volt; 
                Value range: 0 to 400, 
                and the value is accurate to one decimal place (.1).  
                If the value is 2147483647(0x7FFFFFFF), 
                it indicates that the value is invalid. 
                units: V."
            ::= { hwPowerControllerEquipSampEntry 11 }

        hwPowerControllerQtyOfRect  OBJECT-TYPE
            SYNTAX Unsigned32 (0..50)
            MAX-ACCESS read-only
            STATUS current
            DESCRIPTION
                "Number of the rectifiers."
            ::= { hwPowerControllerEquipSampEntry 12 }

        hwPowerControllerRectifierCurrent1 OBJECT-TYPE
            SYNTAX Unsigned32 (0..3000)
            MAX-ACCESS read-only
            STATUS current
            DESCRIPTION
                "Output current of the rectifier module1. It is a real-time analog parameter. Value range: 0 to 300, Units: A, and the value is accurate to one decimal place (.1).  If the value is 2147483647(0x7FFFFFFF), it indicates that the value is invalid."
            ::= { hwPowerControllerEquipSampEntry 13 }

        hwPowerControllerRectifierCurrent2 OBJECT-TYPE
            SYNTAX Unsigned32 (0..3000)
            MAX-ACCESS read-only
            STATUS current
            DESCRIPTION
                "Output current of the rectifier module2. It is a real-time analog parameter. Value range: 0 to 300, Units: A, and the value is accurate to one decimal place (.1).  If the value is 2147483647(0x7FFFFFFF), it indicates that the value is invalid."
            ::= { hwPowerControllerEquipSampEntry 14 }

        hwPowerControllerRectifierCurrent3 OBJECT-TYPE
            SYNTAX Unsigned32 (0..3000)
            MAX-ACCESS read-only
            STATUS current
            DESCRIPTION
                "Output current of the rectifier module3. It is a real-time analog parameter. Value range: 0 to 300, Units: A, and the value is accurate to one decimal place (.1).  If the value is 2147483647(0x7FFFFFFF), it indicates that the value is invalid."
            ::= { hwPowerControllerEquipSampEntry 15 }

        hwPowerControllerRectifierCurrent4 OBJECT-TYPE
            SYNTAX Unsigned32 (0..3000)
            MAX-ACCESS read-only
            STATUS current
            DESCRIPTION
                "Output current of the rectifier module4. It is a real-time analog parameter. Value range: 0 to 300, Units: A, and the value is accurate to one decimal place (.1).  If the value is 2147483647(0x7FFFFFFF), it indicates that the value is invalid."
            ::= { hwPowerControllerEquipSampEntry 16 }

        hwPowerControllerDCVoltage  OBJECT-TYPE
            SYNTAX Unsigned32 (0..1000)
            MAX-ACCESS read-only
            STATUS current
            DESCRIPTION
                "The DC volt; 
                Value range: 0 to 100, 
                and the value is accurate to one decimal place (.1).   
                If the value is 2147483647(0x7FFFFFFF), 
                it indicates that the value is invalid. 
                units: V."
            ::= { hwPowerControllerEquipSampEntry 38 }

        hwPowerControllerTotalLoadCurrent  OBJECT-TYPE
            SYNTAX Integer32 ( -300000..300000)
            MAX-ACCESS read-only
            STATUS current
            DESCRIPTION
                "Load current: -30000 to 30000, 
                
                units: A, 
                
                and the value is one decimal space (.1). If the value is 2147483647(0x7FFFFFFF), it indicates that the value is invalid."
            ::= { hwPowerControllerEquipSampEntry 39 }

        hwPowerControllerBatteryTemperature  OBJECT-TYPE
            SYNTAX Integer32 ( -400..1000)
            MAX-ACCESS read-only
            STATUS current
            DESCRIPTION
                "Battery temperature. It is a battery parameter collected in real time. 
                Value range: -40 to 100, 
                unit: centigrade (degC), 
                and the value is accurate to one decimal place (.1).  
                If the value is 2147483647(0x7FFFFFFF), it indicates that battery temperature is not configured."
            ::= { hwPowerControllerEquipSampEntry 43 }

        hwPowerControllerPhaseL1Volt OBJECT-TYPE
            SYNTAX Unsigned32 ( 0..4000)
            MAX-ACCESS read-only
            STATUS current
            DESCRIPTION
                "The phase L1 voltage; 
                Value range: 0 to 400, 
                and the value is accurate to one decimal place (.1).  
                If the value is 2147483647(0x7FFFFFFF), 
                it indicates that the value is invalid. 
                units: V."
            ::= { hwPowerControllerEquipSampEntry 50 }

        hwPowerControllerPhaseL2Volt OBJECT-TYPE
            SYNTAX Unsigned32 ( 0..4000)
            MAX-ACCESS read-only
            STATUS current
            DESCRIPTION
                "The phase L2 voltage; 
                Value range: 0 to 400, 
                and the value is accurate to one decimal place (.1).  
                If the value is 2147483647(0x7FFFFFFF), 
                it indicates that the value is invalid. 
                units: V."
            ::= { hwPowerControllerEquipSampEntry 51 }

        hwPowerControllerPhaseL3Volt OBJECT-TYPE
            SYNTAX Unsigned32 ( 0..4000)
            MAX-ACCESS read-only
            STATUS current
            DESCRIPTION
                "The phase L3 voltage; 
                Value range: 0 to 400, 
                and the value is accurate to one decimal place (.1).  
                If the value is 2147483647(0x7FFFFFFF), 
                it indicates that the value is invalid. 
                units: V."
            ::= { hwPowerControllerEquipSampEntry 52 }

        hwPVAdapterGroup OBJECT IDENTIFIER ::= { hwSiteMonitorMIBObjects 53 }

        hwPVAdapterGroupSampTable OBJECT-TYPE
            SYNTAX SEQUENCE OF HwPVAdapterGroupSampEntry
            MAX-ACCESS not-accessible
             STATUS current
             DESCRIPTION
                ""
            ::= { hwPVAdapterGroup 1 }

        hwPVAdapterGroupSampEntry OBJECT-TYPE
                        SYNTAX HwPVAdapterGroupSampEntry
            MAX-ACCESS not-accessible
             STATUS current
             DESCRIPTION
                ""
            INDEX { hwPVAdapterGroupIndex }
            ::= { hwPVAdapterGroupSampTable 1 }

        HwPVAdapterGroupSampEntry            ::= SEQUENCE {
                hwPVAdapterGroupIndex
                    Unsigned32,
                hwPVAdapterGroupEquipId
                    Unsigned32,
                hwPVAdapterGroupEquipName
                    OCTET STRING,
                hwPVAdapterGroupTotalOutCurr
                    Unsigned32,
                hwPVAdapterGroupTotalOutPower
                    Unsigned32,
                hwPVAdapterGroupTotalInKW
                    Unsigned32,
                hwPVAdapterGroupTotalOutKW
                    Unsigned32,
                hwPVAdapterGroupFoundNum
                    Unsigned32,
                hwPVAdapterGroupLocateStatus
                    INTEGER,
                hwPVAdapterGroupRunStatus
                    INTEGER,
                hwPVAdapterGroupCommFaultNum
                    Unsigned32
            }

        hwPVAdapterGroupIndex OBJECT-TYPE
            SYNTAX Unsigned32
            MAX-ACCESS read-only
            STATUS current
            DESCRIPTION
                "PV Adapter group table index. Lines of the device list are restricted by the quantity of PV Adapter group."
            ::= { hwPVAdapterGroupSampEntry 1 }

        hwPVAdapterGroupEquipId OBJECT-TYPE
            SYNTAX Unsigned32
            MAX-ACCESS read-only
            STATUS current
            DESCRIPTION
                "PV Adapter group device ID."
            ::= { hwPVAdapterGroupSampEntry 2 }

        hwPVAdapterGroupEquipName OBJECT-TYPE
            SYNTAX OCTET STRING (SIZE (0..63))
            MAX-ACCESS read-only
            STATUS current
            DESCRIPTION
                "PV Adapter group name, of the character string type, is used to specify PV Adapter group.
                
                "
            ::= { hwPVAdapterGroupSampEntry 3 }

        hwPVAdapterGroupTotalOutCurr OBJECT-TYPE
            SYNTAX Unsigned32 (0..100000000)
            MAX-ACCESS read-only
            STATUS current
            DESCRIPTION
                "PV Adapter group total Output current, Value range: 0.0 to 10000000.0.Unit: A.and the value is accurate to one decimal space (.1).  If the value is 2147483647(0x7FFFFFFF), it indicates that the value is invalid."
            ::= { hwPVAdapterGroupSampEntry 4 }

        hwPVAdapterGroupTotalOutPower OBJECT-TYPE
            SYNTAX Unsigned32 (0..4294967295)
            MAX-ACCESS read-only
            STATUS current
            DESCRIPTION
                "The PV Adapter group total output power; 
                Value range: 0 to 4294967295, 
                and the value is accurate to two decimal place (.01), 
                If the value is 2147483647(0x7FFFFFFF), it indicates that the value is invalid."
            ::= { hwPVAdapterGroupSampEntry 5 }

        hwPVAdapterGroupTotalInKW OBJECT-TYPE
            SYNTAX Unsigned32 (0..10000000)
            MAX-ACCESS read-only
            STATUS current
            DESCRIPTION
                "Total input power of the  PV Adapter group. Value range: 0 to 100000, units: kW, and the value is accurate to two decimal place (.01). If the value is 2147483647(0x7FFFFFFF), it indicates that the value is invalid."
            ::= { hwPVAdapterGroupSampEntry 6 }

        hwPVAdapterGroupTotalOutKW OBJECT-TYPE
            SYNTAX Unsigned32 (0..10000000)
            MAX-ACCESS read-only
            STATUS current
            DESCRIPTION
                "Total output power of the PV Adapter group. Value range: 0 to 100000, units: kW, and the value is accurate to two decimal place (.01). If the value is 2147483647(0x7FFFFFFF), it indicates that the value is invalid."
            ::= { hwPVAdapterGroupSampEntry 7 }

        hwPVAdapterGroupFoundNum OBJECT-TYPE
            SYNTAX Unsigned32 (0..100)
            MAX-ACCESS read-only
            STATUS current
            DESCRIPTION
                "The found number in the PV Adapter group; 
                Value range: 0 to 100.   
                If the value is 2147483647(0x7FFFFFFF), it indicates that the value is invalid."
            ::= { hwPVAdapterGroupSampEntry 8 }

        hwPVAdapterGroupLocateStatus OBJECT-TYPE
            SYNTAX INTEGER
                {
                positioningSuccess(1),
                positioningFailed(2),
                notPosition(3),
                Positioning(4),
                unknown(255)
                }
            MAX-ACCESS read-only
            STATUS current
            DESCRIPTION
                "Locate states of the PV Adapter group. It is an enumeration type: 
                  If the enumeration value is 1, it indicates that the PV Adapter positioning success;
                  If the enumeration value is 2, it indicates that the PV Adapter positioning failed.
                  If the enumeration value is 3, it indicates that the PV Adapter not position;
                  If the enumeration value is 4, it indicates that the PV Adapter is positioning;
                  If the enumeration value is 255, it indicates that the PV Adapter is in the unknown state."
            ::= { hwPVAdapterGroupSampEntry 9 }

        hwPVAdapterGroupRunStatus OBJECT-TYPE
            SYNTAX INTEGER
                {
                off(1),
                on(2),
                unknown(255)
                }
            MAX-ACCESS read-only
            STATUS current
            DESCRIPTION
                "Run states of the PV Adapter group. It is an enumeration type: 
                  If the enumeration value is 1, it indicates that the PV Adapter is off;
                  If the enumeration value is 2, it indicates that the PV Adapter is on;
                  If the enumeration value is 255, it indicates that the PV Adapter is in the unknown state."
            ::= { hwPVAdapterGroupSampEntry 10 }

        hwPVAdapterGroupCommFaultNum OBJECT-TYPE
            SYNTAX Unsigned32 (0..100)
            MAX-ACCESS read-only
            STATUS current
            DESCRIPTION
                "The communication failed found number in the PV Adapter group; 
                Value range: 0 to 100.   
                If the value is 2147483647(0x7FFFFFFF), it indicates that the value is invalid."
            ::= { hwPVAdapterGroupSampEntry 11 }

        hwPVAdapterSampTable OBJECT-TYPE
            SYNTAX SEQUENCE OF HwPVAdapterSampEntry
            MAX-ACCESS not-accessible
             STATUS current
             DESCRIPTION
                ""
            ::= { hwPVAdapterGroup 2 }

        hwPVAdapterSampEntry OBJECT-TYPE
                        SYNTAX HwPVAdapterSampEntry
            MAX-ACCESS not-accessible
             STATUS current
             DESCRIPTION
                ""
            INDEX { hwPVAdapterIndex }
            ::= { hwPVAdapterSampTable 1 }

        HwPVAdapterSampEntry            ::= SEQUENCE {
                hwPVAdapterIndex
                    Unsigned32,
                hwPVAdapterEquipId
                    Unsigned32,
                hwPVAdapterEquipName
                    OCTET STRING
            }

        hwPVAdapterIndex OBJECT-TYPE
            SYNTAX Unsigned32
            MAX-ACCESS read-only
            STATUS current
            DESCRIPTION
                "PV Adapter table index. Lines of the device list are restricted by the quantity of PV Adapter group."
            ::= { hwPVAdapterSampEntry 1 }

        hwPVAdapterEquipId OBJECT-TYPE
            SYNTAX Unsigned32
            MAX-ACCESS read-only
            STATUS current
            DESCRIPTION
                "PV Adapter  device ID."
            ::= { hwPVAdapterSampEntry 2 }

        hwPVAdapterEquipName OBJECT-TYPE
            SYNTAX OCTET STRING (SIZE (0..63))
            MAX-ACCESS read-only
            STATUS current
            DESCRIPTION
                "PV Adapter  name, of the character string type, is used to specify PV Adapter .
                
                "
            ::= { hwPVAdapterSampEntry 3 }

        hwSiteMonitorMIBTraps OBJECT IDENTIFIER ::= { hwSiteMonitorMIB 2 }

        hwSiteAlarmTraps OBJECT IDENTIFIER ::= { hwSiteMonitorMIBTraps 1 }

        hwSiteAlarmTrapsPrefix OBJECT IDENTIFIER ::= { hwSiteAlarmTraps 0 }

        hwRectifierFaultAlarmTraps NOTIFICATION-TYPE
            OBJECTS { hwAlarmTrapOrdinalNumber,hwAlarmText,hwAlarmLevel,hwAlarmSigDesc,hwSiteName,hwSiteAdminAddr,hwNetIdentifier,hwSiteDescription,hwRectEquipId,hwRectEquipName,hwRectFatherEquipName,hwRectOperStatus            }
            STATUS current
            DESCRIPTION
                "When rectifiers fault alarms happen, a alarm trap will be send. Its correlation binding parameters: Site ID, Site name, Site description, NE ID, Alarm name, Alarm single description, Alarm port description, Alarm severity, and Site alarm SN. 
                Additionally, in order to identify the device, rectifier equipment ID and equipment name are also include in VB(variable bondings)."
            ::= { hwSiteAlarmTrapsPrefix 1 }

        hwRectifierFaultAlarmResumeTraps NOTIFICATION-TYPE
            OBJECTS { hwAlarmTrapOrdinalNumber,hwAlarmText,hwAlarmLevel,hwAlarmSigDesc,hwSiteName,hwSiteAdminAddr,hwNetIdentifier,hwSiteDescription,hwRectEquipId,hwRectEquipName,hwRectFatherEquipName,hwRectOperStatus            }
            STATUS current
            DESCRIPTION
                "Rectifier Fault alarm resolved.Its correlation binding parameters: Site ID, Site name, Site description, NE ID, Alarm name, Alarm single description, Alarm port description, Alarm severity, and Site alarm SN. Additionally, in order to identify the device, rectifier equipment ID and equipment name are also include in VB(variable bondings)."
            ::= { hwSiteAlarmTrapsPrefix 2 }

        hwRectifierAbnormalAlarmTraps NOTIFICATION-TYPE
            OBJECTS { hwAlarmTrapOrdinalNumber,hwAlarmText,hwAlarmLevel,hwAlarmSigDesc,hwSiteName,hwSiteAdminAddr,hwNetIdentifier,hwSiteDescription,hwRectEquipId,hwRectEquipName,hwRectFatherEquipName,hwRectOperStatus            }
            STATUS current
            DESCRIPTION
                "Rectifier abnormal alarm, because of communication failure, module protection, or turnoff. Its correlation binding parameters:  
                Site ID, Site name, Site description, NE ID, Alarm name, Alarm single description, Alarm port description, Alarm severity, and Site alarm SN. Additionally, in order to identify the device, rectifier equipment ID and equipment name are also include in VB(variable bondings)."
            ::= { hwSiteAlarmTrapsPrefix 3 }

        hwRectifierAbnormalAlarmResumeTraps NOTIFICATION-TYPE
            OBJECTS { hwAlarmTrapOrdinalNumber,hwAlarmText,hwAlarmLevel,hwAlarmSigDesc,hwSiteName,hwSiteAdminAddr,hwNetIdentifier,hwSiteDescription,hwRectEquipId,hwRectEquipName,hwRectFatherEquipName,hwRectOperStatus            }
            STATUS current
            DESCRIPTION
                "Rectifier abnormal alarm resume. Description.Its correlation binding parameters:  Site ID, Site name, Site description, NE ID, Alarm name, Alarm single description, Alarm port description, Alarm severity, and Site alarm SN. Additionally, in order to identify the device, rectifier equipment ID and equipment name are also include in VB(variable bondings)."
            ::= { hwSiteAlarmTrapsPrefix 4 }

        hwBattLoopBreakAlarmTraps NOTIFICATION-TYPE
            OBJECTS { hwAlarmTrapOrdinalNumber,hwAlarmText,hwAlarmLevel,hwAlarmSigDesc,hwSiteName,hwSiteAdminAddr,hwNetIdentifier,hwSiteDescription,hwBattStringEquipId,hwBattStringEquipName,hwBattStringFatherEquipname,hwBattStringOperStatus            }
            STATUS current
            DESCRIPTION
                "Battery loop disconnect. Its correlation binding parameters:  Site ID, Site name, Site description, NE ID, Alarm name, Alarm single description, Alarm port description, Alarm severity, and Site alarm SN. Additionally, in order to identify the device, battery string equipment ID and equipment name are also include in VB(variable bondings)."
            ::= { hwSiteAlarmTrapsPrefix 5 }

        hwBattLoopBreakAlarmResumeTraps NOTIFICATION-TYPE
            OBJECTS { hwAlarmTrapOrdinalNumber,hwAlarmText,hwAlarmLevel,hwAlarmSigDesc,hwSiteName,hwSiteAdminAddr,hwNetIdentifier,hwSiteDescription,hwBattStringEquipId,hwBattStringEquipName,hwBattStringFatherEquipname,hwBattStringOperStatus            }
            STATUS current
            DESCRIPTION
                "Battery loop break alarm resume. Its correlation binding parameters:  Site ID, Site name, Site description, NE ID, Alarm name, Alarm single description, Alarm port description, Alarm severity, and Site alarm SN. Additionally, in order to identify the device, battery string equipment ID and equipment name are also include in VB(variable bondings)."
            ::= { hwSiteAlarmTrapsPrefix 6 }

        hwBattLvdAlarmTraps NOTIFICATION-TYPE
            OBJECTS { hwAlarmTrapOrdinalNumber,hwAlarmText,hwAlarmLevel,hwAlarmSigDesc,hwSiteName,hwSiteAdminAddr,hwNetIdentifier,hwSiteDescription,hwBattsGroupId,hwBattsGroupName            }
            STATUS current
            DESCRIPTION
                "Battery disconnect for low voltage. Its correlation binding parameters:  Site ID, Site name, Site description, NE ID, Alarm name, Alarm single description, Alarm port description, Alarm severity, and Site alarm SN. 
                Additionally, in order to identify the device, battery LVD unit equipment ID and equipment name are also include in VB(variable bondings)."
            ::= { hwSiteAlarmTrapsPrefix 7 }

        hwBattLvdAlarmResumeTraps NOTIFICATION-TYPE
            OBJECTS { hwAlarmTrapOrdinalNumber,hwAlarmText,hwAlarmLevel,hwAlarmSigDesc,hwSiteName,hwSiteAdminAddr,hwNetIdentifier,hwSiteDescription,hwBattsGroupId,hwBattsGroupName            }
            STATUS current
            DESCRIPTION
                "Battery LVD alarm resume. Its correlation binding parameters:  Site ID, Site name, Site description, NE ID, Alarm name, Alarm single description, Alarm port description, Alarm severity, and Site alarm SN. Additionally, in order to identify the device, battery LVD unit equipment ID and equipment name are also include in VB(variable bondings)."
            ::= { hwSiteAlarmTrapsPrefix 8 }

        hwBattOverCurrAlarmTraps NOTIFICATION-TYPE
            OBJECTS { hwAlarmTrapOrdinalNumber,hwAlarmText,hwAlarmLevel,hwAlarmSigDesc,hwSiteName,hwSiteAdminAddr,hwNetIdentifier,hwSiteDescription,hwBattsGroupId,hwBattsGroupName            }
            STATUS current
            DESCRIPTION
                "Batterys charge in over current. Its correlation binding parameters:  Site ID, Site name, Site description, NE ID, Alarm name, Alarm single description, Alarm port description, Alarm severity, and Site alarm SN. Additionally, in order to identify the device, battery string equipment ID and equipment name are also include in VB(variable bondings)."
            ::= { hwSiteAlarmTrapsPrefix 9 }

        hwBattOverCurrAlarmResumeTraps NOTIFICATION-TYPE
            OBJECTS { hwAlarmTrapOrdinalNumber,hwAlarmText,hwAlarmLevel,hwAlarmSigDesc,hwSiteName,hwSiteAdminAddr,hwNetIdentifier,hwSiteDescription,hwBattsGroupId,hwBattsGroupName            }
            STATUS current
            DESCRIPTION
                "Batterys over current alarm resume. Its correlation binding parameters:  Site ID, Site name, Site description, NE ID, Alarm name, Alarm single description, Alarm port description, Alarm severity, and Site alarm SN. Additionally, in order to identify the device, battery string equipment ID and equipment name are also include in VB(variable bondings)."
            ::= { hwSiteAlarmTrapsPrefix 10 }

        hwBattStringTempAlarmTraps NOTIFICATION-TYPE
            OBJECTS { hwAlarmTrapOrdinalNumber,hwAlarmText,hwAlarmLevel,hwAlarmSigDesc,hwSiteName,hwSiteAdminAddr,hwNetIdentifier,hwSiteDescription,hwBattsGroupId,hwBattsGroupName            }
            STATUS current
            DESCRIPTION
                "Battery string temperature is too high or too low. Its correlation binding parameters:  Site ID, Site name, Site description, NE ID, Alarm name, Alarm single description, Alarm port description, Alarm severity, and Site alarm SN. Additionally, in order to identify the device, battery group ID and group name are also include in VB(variable bondings)."
            ::= { hwSiteAlarmTrapsPrefix 11 }

        hwBattStringTempAlarmResumeTraps NOTIFICATION-TYPE
            OBJECTS { hwAlarmTrapOrdinalNumber,hwAlarmText,hwAlarmLevel,hwAlarmSigDesc,hwSiteName,hwSiteAdminAddr,hwNetIdentifier,hwSiteDescription,hwBattsGroupId,hwBattsGroupName            }
            STATUS current
            DESCRIPTION
                "Battery string temperature alarm resume. Its correlation binding parameters:  Site ID, Site name, Site description, NE ID, Alarm name, Alarm single description, Alarm port description, Alarm severity, and Site alarm SN. Additionally, in order to identify the device, battery group ID and group name are also include in VB(variable bondings)."
            ::= { hwSiteAlarmTrapsPrefix 12 }

        hwBattDischargeAlarmTraps NOTIFICATION-TYPE
            OBJECTS { hwAlarmTrapOrdinalNumber,hwAlarmText,hwAlarmLevel,hwAlarmSigDesc,hwSiteName,hwSiteAdminAddr,hwNetIdentifier,hwSiteDescription,hwBattsGroupId,hwBattsGroupName            }
            STATUS current
            DESCRIPTION
                "Battery group discharge alarm. Its correlation binding parameters:  Site ID, Site name, Site description, NE ID, Alarm name, Alarm single description, Alarm port description, Alarm severity, and Site alarm SN. Additionally, in order to identify the device, battery group ID and group name are also include in VB(variable bondings)."
            ::= { hwSiteAlarmTrapsPrefix 13 }

        hwBattDischargeAlarmResumeTraps NOTIFICATION-TYPE
            OBJECTS { hwAlarmTrapOrdinalNumber,hwAlarmText,hwAlarmLevel,hwAlarmSigDesc,hwSiteName,hwSiteAdminAddr,hwNetIdentifier,hwSiteDescription,hwBattsGroupId,hwBattsGroupName            }
            STATUS current
            DESCRIPTION
                "Battery group discharge alarm resume. Its correlation binding parameters:  Site ID, Site name, Site description, NE ID, Alarm name, Alarm single description, Alarm port description, Alarm severity, and Site alarm SN. Additionally, in order to identify the device, battery group ID and group name are also include in VB(variable bondings)."
            ::= { hwSiteAlarmTrapsPrefix 14 }

        hwAcInputAlarmTraps NOTIFICATION-TYPE
            OBJECTS { hwAlarmTrapOrdinalNumber,hwAlarmText,hwAlarmLevel,hwAlarmSigDesc,hwSiteName,hwSiteAdminAddr,hwNetIdentifier,hwSiteDescription,hwAcEquipId,hwAcEquipName,hwAcFatherEquipname,hwAcInputOperStatus            }
            STATUS current
            DESCRIPTION
                "AC absent or AC power off alarms happened. Its correlation binding parameters:  Site ID, Site name, Site description, NE ID, Alarm name, Alarm single description, Alarm port description, Alarm severity, and Site alarm SN. Additionally, in order to identify the device, AC equipment ID and equipment name are also include in VB(variable bondings)."
            ::= { hwSiteAlarmTrapsPrefix 15 }

        hwAcInputAlarmResumeTraps NOTIFICATION-TYPE
            OBJECTS { hwAlarmTrapOrdinalNumber,hwAlarmText,hwAlarmLevel,hwAlarmSigDesc,hwSiteName,hwSiteAdminAddr,hwNetIdentifier,hwSiteDescription,hwAcEquipId,hwAcEquipName,hwAcFatherEquipname,hwAcInputOperStatus            }
            STATUS current
            DESCRIPTION
                "AC input alarm resumed. Its correlation binding parameters:  Site ID, Site name, Site description, NE ID, Alarm name, Alarm single description, Alarm port description, Alarm severity, and Site alarm SN. Additionally, in order to identify the device, AC equipment ID and equipment name are also include in VB(variable bondings)."
            ::= { hwSiteAlarmTrapsPrefix 16 }

        hwAcVoltAlarmTraps NOTIFICATION-TYPE
            OBJECTS { hwAlarmTrapOrdinalNumber,hwAlarmText,hwAlarmLevel,hwAlarmSigDesc,hwSiteName,hwSiteAdminAddr,hwNetIdentifier,hwSiteDescription,hwAcEquipId,hwAcEquipName,hwAcInputOperStatus            }
            STATUS current
            DESCRIPTION
                "AC voltage too high or too low. Its correlation binding parameters:  Site ID, Site name, Site description, NE ID, Alarm name, Alarm single description, Alarm port description, Alarm severity, and Site alarm SN. Additionally, in order to identify the device, AC equipment ID and equipment name are also include in VB(variable bondings)."
            ::= { hwSiteAlarmTrapsPrefix 17 }

        hwAcVoltAlarmResumeTraps NOTIFICATION-TYPE
            OBJECTS { hwAlarmTrapOrdinalNumber,hwAlarmText,hwAlarmLevel,hwAlarmSigDesc,hwSiteName,hwSiteAdminAddr,hwNetIdentifier,hwSiteDescription,hwAcEquipId,hwAcEquipName,hwAcInputOperStatus            }
            STATUS current
            DESCRIPTION
                "AC voltage alarm resume. Its correlation binding parameters:  Site ID, Site name, Site description, NE ID, Alarm name, Alarm single description, Alarm port description, Alarm severity, and Site alarm SN. Additionally, in order to identify the device, AC equipment ID and equipment name are also include in VB(variable bondings)."
            ::= { hwSiteAlarmTrapsPrefix 18 }

        hwDcVoltAlarmTraps NOTIFICATION-TYPE
            OBJECTS { hwAlarmTrapOrdinalNumber,hwAlarmText,hwAlarmLevel,hwAlarmSigDesc,hwSiteName,hwSiteAdminAddr,hwNetIdentifier,hwSiteDescription,hwDcOutputEquipId,hwDcOutputEquipName,hwDcFatherEquipname,hwDcOutputOperStatus            }
            STATUS current
            DESCRIPTION
                "DC voltage alarm. Its correlation binding parameters:  Site ID, Site name, Site description, NE ID, Alarm name, Alarm single description, Alarm port description, Alarm severity, and Site alarm SN. Additionally, in order to identify the device, AC equipment ID and equipment name are also include in VB(variable bondings)."
            ::= { hwSiteAlarmTrapsPrefix 19 }

        hwDcVoltAlarmResumeTraps NOTIFICATION-TYPE
            OBJECTS { hwAlarmTrapOrdinalNumber,hwAlarmText,hwAlarmLevel,hwAlarmSigDesc,hwSiteName,hwSiteAdminAddr,hwNetIdentifier,hwSiteDescription,hwDcOutputEquipId,hwDcOutputEquipName,hwDcFatherEquipname,hwDcOutputOperStatus            }
            STATUS current
            DESCRIPTION
                "DC voltage alarm resume. Its correlation binding parameters:  Site ID, Site name, Site description, NE ID, Alarm name, Alarm single description, Alarm port description, Alarm severity, and Site alarm SN. Additionally, in order to identify the device, DC equipment ID and equipment name are also include in VB(variable bondings)."
            ::= { hwSiteAlarmTrapsPrefix 20 }

        hwLoadLvdAlarmTraps NOTIFICATION-TYPE
            OBJECTS { hwAlarmTrapOrdinalNumber,hwAlarmText,hwAlarmLevel,hwAlarmSigDesc,hwSiteName,hwSiteAdminAddr,hwNetIdentifier,hwSiteDescription,hwDcOutputEquipId,hwDcOutputEquipName,hwDcFatherEquipname            }
            STATUS current
            DESCRIPTION
                "Loads disconnect for low voltage. Its correlation binding parameters:  Site ID, Site name, Site description, NE ID, Alarm name, Alarm single description, Alarm port description, Alarm severity, and Site alarm SN. Additionally, in order to identify the device, load LVD unit equipment ID and equipment name are also include in VB(variable bondings)."
            ::= { hwSiteAlarmTrapsPrefix 21 }

        hwLoadLvdAlarmResumeTraps NOTIFICATION-TYPE
            OBJECTS { hwAlarmTrapOrdinalNumber,hwAlarmText,hwAlarmLevel,hwAlarmSigDesc,hwSiteName,hwSiteAdminAddr,hwNetIdentifier,hwSiteDescription,hwDcOutputEquipId,hwDcOutputEquipName,hwDcFatherEquipname            }
            STATUS current
            DESCRIPTION
                "Load LVD alarm resume. Its correlation binding parameters:  Site ID, Site name, Site description, NE ID, Alarm name, Alarm single description, Alarm port description, Alarm severity, and Site alarm SN. Additionally, in order to identify the device, load LVD unit equipment ID and equipment name are also include in VB(variable bondings)."
            ::= { hwSiteAlarmTrapsPrefix 22 }

        hwLoadFuseAlarmTraps NOTIFICATION-TYPE
            OBJECTS { hwAlarmTrapOrdinalNumber,hwAlarmText,hwAlarmLevel,hwAlarmSigDesc,hwSiteName,hwSiteAdminAddr,hwNetIdentifier,hwSiteDescription,hwDcOutputEquipId,hwDcOutputEquipName,hwDcFatherEquipname            }
            STATUS current
            DESCRIPTION
                "Load fuse broken down. Its correlation binding parameters:  Site ID, Site name, Site description, NE ID, Alarm name, Alarm single description, Alarm port description, Alarm severity, and Site alarm SN. Additionally, in order to identify the device, load branch equipment ID and equipment name are also include in VB(variable bondings)."
            ::= { hwSiteAlarmTrapsPrefix 23 }

        hwLoadFuseAlarmResumeTraps NOTIFICATION-TYPE
            OBJECTS { hwAlarmTrapOrdinalNumber,hwAlarmText,hwAlarmLevel,hwAlarmSigDesc,hwSiteName,hwSiteAdminAddr,hwNetIdentifier,hwSiteDescription,hwDcOutputEquipId,hwDcOutputEquipName,hwDcFatherEquipname            }
            STATUS current
            DESCRIPTION
                "Load fuse alarm resume. Its correlation binding parameters:  Site ID, Site name, Site description, NE ID, Alarm name, Alarm single description, Alarm port description, Alarm severity, and Site alarm SN. Additionally, in order to identify the device, load branch equipment ID and equipment name are also include in VB(variable bondings)."
            ::= { hwSiteAlarmTrapsPrefix 24 }

        hwEnvTempAlarmTraps NOTIFICATION-TYPE
            OBJECTS { hwAlarmTrapOrdinalNumber,hwAlarmText,hwAlarmLevel,hwAlarmSigDesc,hwSiteName,hwSiteAdminAddr,hwNetIdentifier,hwSiteDescription,hwEnvTempEquipId,hwEnvTempEquipName,hwEnvTempFatherEquipname,hwEnvTempSensorOperStatus            }
            STATUS current
            DESCRIPTION
                "Environment temperature is too high or too low. Its correlation binding parameters:  Site ID, Site name, Site description, NE ID, Alarm name, Alarm single description, Alarm port description, Alarm severity, and Site alarm SN. Additionally, in order to identify the device, envirenment temperature sensor equipment ID ,name and father equip name are also include in VB(variable bondings).    "
            ::= { hwSiteAlarmTrapsPrefix 25 }

        hwEnvTempAlarmResumeTraps NOTIFICATION-TYPE
            OBJECTS { hwAlarmTrapOrdinalNumber,hwAlarmText,hwAlarmLevel,hwAlarmSigDesc,hwSiteName,hwSiteAdminAddr,hwNetIdentifier,hwSiteDescription,hwEnvTempEquipId,hwEnvTempEquipName,hwEnvTempFatherEquipname,hwEnvTempSensorOperStatus            }
            STATUS current
            DESCRIPTION
                "Environment temperature alarm resume. Its correlation binding parameters:  Site ID, Site name, Site description, NE ID, Alarm name, Alarm single description, Alarm port description, Alarm severity, and Site alarm SN. Additionally, in order to identify the device, envirenment temperature sensor equipment ID, name and father equip name are also include in VB(variable bondings).    "
            ::= { hwSiteAlarmTrapsPrefix 26 }

        hwEnvHumiAlarmTraps NOTIFICATION-TYPE
            OBJECTS { hwAlarmTrapOrdinalNumber,hwAlarmText,hwAlarmLevel,hwAlarmSigDesc,hwSiteName,hwSiteAdminAddr,hwNetIdentifier,hwSiteDescription,hwEnvHumiEquipId,hwEnvHumiEquipName,hwEnvHumiFatherEquipname,hwEnvHumiSensorOperStatus            }
            STATUS current
            DESCRIPTION
                "Environment humidity is too high or too low. Its correlation binding parameters:  Site ID, Site name, Site description, NE ID, Alarm name, Alarm single description, Alarm port description, Alarm severity, and Site alarm SN. Additionally, in order to identify the device, envirenment humidity sensor equipment ID, name and father equip nameare also include in VB(variable bondings)."
            ::= { hwSiteAlarmTrapsPrefix 27 }

        hwEnvHumiAlarmResumeTraps NOTIFICATION-TYPE
            OBJECTS { hwAlarmTrapOrdinalNumber,hwAlarmText,hwAlarmLevel,hwAlarmSigDesc,hwSiteName,hwSiteAdminAddr,hwNetIdentifier,hwSiteDescription,hwEnvHumiEquipId,hwEnvHumiEquipName,hwEnvHumiFatherEquipname,hwEnvHumiSensorOperStatus            }
            STATUS current
            DESCRIPTION
                "Environment humidity alarm resume. Its correlation binding parameters:  Site ID, Site name, Site description, NE ID, Alarm name, Alarm single description, Alarm port description, Alarm severity, and Site alarm SN. Additionally, in order to identify the device, envirenment humidity sensor equipment ID, name and father equip name are also include in VB(variable bondings)."
            ::= { hwSiteAlarmTrapsPrefix 28 }

        hwSpareDigitalAlarmTraps NOTIFICATION-TYPE
            OBJECTS { hwAlarmTrapOrdinalNumber,hwAlarmText,hwAlarmLevel,hwAlarmSigDesc,hwSiteName,hwSiteAdminAddr,hwNetIdentifier,hwSiteDescription,hwDeviceUimEquipId,hwDeviceUimEquipName,hwDeviceUimFatherEquipname            }
            STATUS current
            DESCRIPTION
                "Spare digital fault. Its correlation binding parameters:  Site ID, Site name, Site description, NE ID, Alarm name, Alarm single description, Alarm port description, Alarm severity, and Site alarm SN. Additionally, in order to identify the device, Spare digital equipment ID and equipment name are also include in VB(variable bondings)."
            ::= { hwSiteAlarmTrapsPrefix 29 }

        hwSpareDigitalAlarmResumeTraps NOTIFICATION-TYPE
            OBJECTS { hwAlarmTrapOrdinalNumber,hwAlarmText,hwAlarmLevel,hwAlarmSigDesc,hwSiteName,hwSiteAdminAddr,hwNetIdentifier,hwSiteDescription,hwDeviceUimEquipId,hwDeviceUimEquipName,hwDeviceUimFatherEquipname            }
            STATUS current
            DESCRIPTION
                "Spare digital alarm resume.Its correlation binding parameters:  Site ID, Site name, Site description, NE ID, Alarm name, Alarm single description, Alarm port description, Alarm severity, and Site alarm SN. Additionally, in order to identify the device, Spare digital equipment ID and equipment name are also include in VB(variable bondings)."
            ::= { hwSiteAlarmTrapsPrefix 30 }

        hwDoorAlarmTraps NOTIFICATION-TYPE
            OBJECTS { hwAlarmTrapOrdinalNumber,hwAlarmText,hwAlarmLevel,hwAlarmSigDesc,hwSiteName,hwSiteAdminAddr,hwNetIdentifier,hwSiteDescription,hwDoorSensorEquipId,hwDoorEquipName,hwDoorSensorFatherEquipname            }
            STATUS current
            DESCRIPTION
                "Door open. Its correlation binding parameters:  Site ID, Site name, Site description, NE ID, Alarm name, Alarm single description, Alarm port description, Alarm severity, and Site alarm SN. Additionally, in order to identify the device, equip ID、equip name、father equip name are also include in VB(variable bondings)."
            ::= { hwSiteAlarmTrapsPrefix 31 }

        hwDoorAlarmResumeTraps NOTIFICATION-TYPE
            OBJECTS { hwAlarmTrapOrdinalNumber,hwAlarmText,hwAlarmLevel,hwAlarmSigDesc,hwSiteName,hwSiteAdminAddr,hwNetIdentifier,hwSiteDescription,hwDoorSensorEquipId,hwDoorEquipName,hwDoorSensorFatherEquipname            }
            STATUS current
            DESCRIPTION
                "Door alarm resume. Its correlation binding parameters:  Site ID, Site name, Site description, NE ID, Alarm name, Alarm single description, Alarm port description, Alarm severity, and Site alarm SN. Additionally, in order to identify the device, equip ID、equip name、father equip name are also include in VB(variable bondings)."
            ::= { hwSiteAlarmTrapsPrefix 32 }

        hwWaterAlarmTraps NOTIFICATION-TYPE
            OBJECTS { hwAlarmTrapOrdinalNumber,hwAlarmText,hwAlarmLevel,hwAlarmSigDesc,hwSiteName,hwSiteAdminAddr,hwNetIdentifier,hwSiteDescription,hwWaterSensorEquipId,hwWaterEquipName,hwWaterSensorFatherEquipname            }
            STATUS current
            DESCRIPTION
                "Water alarm. Its correlation binding parameters:  Site ID, Site name, Site description, NE ID, Alarm name, Alarm single description, Alarm port description, Alarm severity, and Site alarm SN. Additionally, in order to identify the device, equip ID、equip name、father equip name are also include in VB(variable bondings)."
            ::= { hwSiteAlarmTrapsPrefix 33 }

        hwWaterAlarmResumeTraps NOTIFICATION-TYPE
            OBJECTS { hwAlarmTrapOrdinalNumber,hwAlarmText,hwAlarmLevel,hwAlarmSigDesc,hwSiteName,hwSiteAdminAddr,hwNetIdentifier,hwSiteDescription,hwWaterSensorEquipId,hwWaterEquipName,hwWaterSensorFatherEquipname            }
            STATUS current
            DESCRIPTION
                "Water alarm resume. Its correlation binding parameters:  Site ID, Site name, Site description, NE ID, Alarm name, Alarm single description, Alarm port description, Alarm severity, and Site alarm SN. Additionally, in order to identify the device, equip ID、equip name、father equip name are also include in VB(variable bondings)."
            ::= { hwSiteAlarmTrapsPrefix 34 }

        hwSmokeAlarmTraps NOTIFICATION-TYPE
            OBJECTS { hwAlarmTrapOrdinalNumber,hwAlarmText,hwAlarmLevel,hwAlarmSigDesc,hwSiteName,hwSiteAdminAddr,hwNetIdentifier,hwSiteDescription,hwSmokeSensorEquipId,hwSmokeEquipName,hwSmokeSensorFatherEquipname            }
            STATUS current
            DESCRIPTION
                "Site is on fire, which is detected by smoke sensors. Its correlation binding parameters:  Site ID, Site name, Site description, NE ID, Alarm name, Alarm single description, Alarm port description, Alarm severity, and Site alarm SN. Additionally, in order to identify the device, equip ID、equip name、father equip name are also include in VB(variable bondings)."
            ::= { hwSiteAlarmTrapsPrefix 35 }

        hwSmokeAlarmResumeTraps NOTIFICATION-TYPE
            OBJECTS { hwAlarmTrapOrdinalNumber,hwAlarmText,hwAlarmLevel,hwAlarmSigDesc,hwSiteName,hwSiteAdminAddr,hwNetIdentifier,hwSiteDescription,hwSmokeSensorEquipId,hwSmokeEquipName,hwSmokeSensorFatherEquipname            }
            STATUS current
            DESCRIPTION
                "Smoke alarm resume. Its correlation binding parameters:  Site ID, Site name, Site description, NE ID, Alarm name, Alarm single description, Alarm port description, Alarm severity, and Site alarm SN. Additionally, in order to identify the device, equip ID、equip name、father equip name are also include in VB(variable bondings)."
            ::= { hwSiteAlarmTrapsPrefix 36 }

        hwWireAlarmTraps NOTIFICATION-TYPE
            OBJECTS { hwAlarmTrapOrdinalNumber,hwAlarmText,hwAlarmLevel,hwAlarmSigDesc,hwSiteName,hwSiteAdminAddr,hwNetIdentifier,hwSiteDescription,hwEnvUnitsGroupId,hwEnvUnitsGroupName            }
            STATUS current
            DESCRIPTION
                "Wire alarm.Its correlation binding parameters:  Site ID, Site name, Site description, NE ID, Alarm name, Alarm single description, Alarm port description, Alarm severity, and Site alarm SN. Additionally, in order to identify the device, envirenment unit group ID and group name are also include in VB(variable bondings)."
            ::= { hwSiteAlarmTrapsPrefix 37 }

        hwWireAlarmResumeTraps NOTIFICATION-TYPE
            OBJECTS { hwAlarmTrapOrdinalNumber,hwAlarmText,hwAlarmLevel,hwAlarmSigDesc,hwSiteName,hwSiteAdminAddr,hwNetIdentifier,hwSiteDescription,hwEnvUnitsGroupId,hwEnvUnitsGroupName            }
            STATUS current
            DESCRIPTION
                "Wire alarm resume. Its correlation binding parameters:  Site ID, Site name, Site description, NE ID, Alarm name, Alarm single description, Alarm port description, Alarm severity, and Site alarm SN. Additionally, in order to identify the device, envirenment unit group ID and group name are also include in VB(variable bondings)."
            ::= { hwSiteAlarmTrapsPrefix 38 }

        hwAcBreakerAlarmTraps NOTIFICATION-TYPE
            OBJECTS { hwAlarmTrapOrdinalNumber,hwAlarmText,hwAlarmLevel,hwAlarmSigDesc,hwSiteName,hwSiteAdminAddr,hwNetIdentifier,hwSiteDescription            }
            STATUS current
            DESCRIPTION
                "AC breaker alarm.Its correlation binding parameters:  Site ID, Site name, Site description, NE ID, Alarm name, Alarm single description, Alarm port description, Alarm severity, and Site alarm SN. Additionally, in order to identify the device, AC distribution unit ID and its name are also include in VB(variable bondings)."
            ::= { hwSiteAlarmTrapsPrefix 39 }

        hwAcBreakerAlarmResumeTraps NOTIFICATION-TYPE
            OBJECTS { hwAlarmTrapOrdinalNumber,hwAlarmText,hwAlarmLevel,hwAlarmSigDesc,hwSiteName,hwSiteAdminAddr,hwNetIdentifier,hwSiteDescription            }
            STATUS current
            DESCRIPTION
                "AC breaker alarm resume.Its correlation binding parameters:  Site ID, Site name, Site description, NE ID, Alarm name, Alarm single description, Alarm port description, Alarm severity, and Site alarm SN. Additionally, in order to identify the device, AC distribution unit ID and its name are also include in VB(variable bondings)."
            ::= { hwSiteAlarmTrapsPrefix 40 }

        hwMultiRectFailureAlarmTraps NOTIFICATION-TYPE
            OBJECTS { hwAlarmTrapOrdinalNumber,hwAlarmText,hwAlarmLevel,hwAlarmSigDesc,hwSiteName,hwSiteAdminAddr,hwNetIdentifier,hwSiteDescription,hwRectsGroupId,hwRectsGroupName            }
            STATUS current
            DESCRIPTION
                "More than one rectifier reported fault alarms in the same time. Its correlation binding parameters:  Site ID, Site name, Site description, NE ID, Alarm name, Alarm single description, Alarm port description, Alarm severity, and Site alarm SN. Additionally, in order to identify the device, rectifier group ID and group name are also include in VB(variable bondings)."
            ::= { hwSiteAlarmTrapsPrefix 41 }

        hwMultiRectFailureAlarmResumeTraps NOTIFICATION-TYPE
            OBJECTS { hwAlarmTrapOrdinalNumber,hwAlarmText,hwAlarmLevel,hwAlarmSigDesc,hwSiteName,hwSiteAdminAddr,hwNetIdentifier,hwSiteDescription,hwRectsGroupId,hwRectsGroupName            }
            STATUS current
            DESCRIPTION
                "Multi-rectifiers fault alarm resume. Its correlation binding parameters:  Site ID, Site name, Site description, NE ID, Alarm name, Alarm single description, Alarm port description, Alarm severity, and Site alarm SN. Additionally, in order to identify the device, rectifier group ID and group name are also include in VB(variable bondings)."
            ::= { hwSiteAlarmTrapsPrefix 42 }

        hwRectRedundAlarmTraps NOTIFICATION-TYPE
            OBJECTS { hwAlarmTrapOrdinalNumber,hwAlarmText,hwAlarmLevel,hwAlarmSigDesc,hwSiteName,hwSiteAdminAddr,hwNetIdentifier,hwSiteDescription,hwRectsGroupId,hwRectsGroupName            }
            STATUS current
            DESCRIPTION
                "Rectifiers work redundantly, in this case that some of rectifiers will going to sleep. Its correlation binding parameters:  Site ID, Site name, Site description, NE ID, Alarm name, Alarm single description, Alarm port description, Alarm severity, and Site alarm SN. Additionally, in order to identify the device, rectifier group ID and group name are also include in VB(variable bondings)."
            ::= { hwSiteAlarmTrapsPrefix 43 }

        hwRectRedundAlarmResumeTraps NOTIFICATION-TYPE
            OBJECTS { hwAlarmTrapOrdinalNumber,hwAlarmText,hwAlarmLevel,hwAlarmSigDesc,hwSiteName,hwSiteAdminAddr,hwNetIdentifier,hwSiteDescription,hwRectsGroupId,hwRectsGroupName            }
            STATUS current
            DESCRIPTION
                "Rectifiers redundant alarm resume, when the power supply and requirement were in balance. Its correlation binding parameters:  Site ID, Site name, Site description, NE ID, Alarm name, Alarm single description, Alarm port description, Alarm severity, and Site alarm SN. Additionally, in order to identify the device, rectifier group ID and group name are also include in VB(variable bondings)."
            ::= { hwSiteAlarmTrapsPrefix 44 }

        hwBattUnbalanceAlarmTraps NOTIFICATION-TYPE
            OBJECTS { hwAlarmTrapOrdinalNumber,hwAlarmText,hwAlarmLevel,hwAlarmSigDesc,hwSiteName,hwSiteAdminAddr,hwNetIdentifier,hwSiteDescription,hwBattStringEquipId,hwBattStringEquipName,hwBattStringFatherEquipname,hwBattStringOperStatus            }
            STATUS current
            DESCRIPTION
                "Battery works in unbalance state. Its correlation binding parameters:  Site ID, Site name, Site description, NE ID, Alarm name, Alarm single description, Alarm port description, Alarm severity, and Site alarm SN. Additionally, in order to identify the device, battery string equipment ID and equipment name are also include in VB(variable bondings)."
            ::= { hwSiteAlarmTrapsPrefix 45 }

        hwBattUnbalanceAlarmResumeTraps NOTIFICATION-TYPE
            OBJECTS { hwAlarmTrapOrdinalNumber,hwAlarmText,hwAlarmLevel,hwAlarmSigDesc,hwSiteName,hwSiteAdminAddr,hwNetIdentifier,hwSiteDescription,hwBattStringEquipId,hwBattStringEquipName,hwBattStringFatherEquipname,hwBattStringOperStatus            }
            STATUS current
            DESCRIPTION
                "Battery unbalance alarm resume. Its correlation binding parameters:  Site ID, Site name, Site description, NE ID, Alarm name, Alarm single description, Alarm port description, Alarm severity, and Site alarm SN. Additionally, in order to identify the device, battery string equipment ID and equipment name are also include in VB(variable bondings)."
            ::= { hwSiteAlarmTrapsPrefix 46 }

        hwAcFreqFaultAlarmTraps NOTIFICATION-TYPE
            OBJECTS { hwAlarmTrapOrdinalNumber,hwAlarmText,hwAlarmLevel,hwAlarmSigDesc,hwSiteName,hwSiteAdminAddr,hwNetIdentifier,hwSiteDescription,hwAcEquipId,hwAcEquipName,hwAcFatherEquipname,hwAcInputOperStatus            }
            STATUS current
            DESCRIPTION
                "AC frequency is fault. Its correlation binding parameters:  Site ID, Site name, Site description, NE ID, Alarm name, Alarm single description, Alarm port description, Alarm severity, and Site alarm SN. Additionally, in order to identify the device, AC equipment ID and equipment name are also include in VB(variable bondings)."
            ::= { hwSiteAlarmTrapsPrefix 47 }

        hwAcFreqFaultAlarmResumeTraps NOTIFICATION-TYPE
            OBJECTS { hwAlarmTrapOrdinalNumber,hwAlarmText,hwAlarmLevel,hwAlarmSigDesc,hwSiteName,hwSiteAdminAddr,hwNetIdentifier,hwSiteDescription,hwAcEquipId,hwAcEquipName,hwAcFatherEquipname,hwAcInputOperStatus            }
            STATUS current
            DESCRIPTION
                "AC frequency alarm resume. Its correlation binding parameters:  Site ID, Site name, Site description, NE ID, Alarm name, Alarm single description, Alarm port description, Alarm severity, and Site alarm SN. Additionally, in order to identify the device, AC equipment ID and equipment name are also include in VB(variable bondings)."
            ::= { hwSiteAlarmTrapsPrefix 48 }

        hwXmuSelfFaultAlarmTraps NOTIFICATION-TYPE
            OBJECTS { hwAlarmTrapOrdinalNumber,hwAlarmText,hwAlarmLevel,hwAlarmSigDesc,hwSiteName,hwSiteAdminAddr,hwNetIdentifier,hwSiteDescription,hwMonEquipId,hwMonEquipName,hwMonitorOperStatus            }
            STATUS current
            DESCRIPTION
                "There are some fault in XMU itself. Its correlation binding parameters:  Site ID, Site name, Site description, NE ID, Alarm name, Alarm single description, Alarm port description, Alarm severity, and Site alarm SN. Additionally, in order to identify the device, monitor equipment ID and equipment name are also include in VB(variable bondings)."
            ::= { hwSiteAlarmTrapsPrefix 49 }

        hwXmuSelfFaultAlarmResumeTraps NOTIFICATION-TYPE
            OBJECTS { hwAlarmTrapOrdinalNumber,hwAlarmText,hwAlarmLevel,hwAlarmSigDesc,hwSiteName,hwSiteAdminAddr,hwNetIdentifier,hwSiteDescription,hwMonEquipId,hwMonEquipName,hwMonitorOperStatus            }
            STATUS current
            DESCRIPTION
                "XMU fault alarm resume. Its correlation binding parameters:  Site ID, Site name, Site description, NE ID, Alarm name, Alarm single description, Alarm port description, Alarm severity, and Site alarm SN. Additionally, in order to identify the device, monitor equipment ID and equipment name are also include in VB(variable bondings)."
            ::= { hwSiteAlarmTrapsPrefix 50 }

        hwRs485CommAlarmTraps NOTIFICATION-TYPE
            OBJECTS { hwAlarmTrapOrdinalNumber,hwAlarmText,hwAlarmLevel,hwAlarmSigDesc,hwSiteName,hwSiteAdminAddr,hwNetIdentifier,hwSiteDescription,hwMonEquipId,hwMonEquipName,hwMonitorOperStatus            }
            STATUS current
            DESCRIPTION
                "RS485 communication of monitors disconnect. Its correlation binding parameters:  Site ID, Site name, Site description, NE ID, Alarm name, Alarm single description, Alarm port description, Alarm severity, and Site alarm SN. Additionally, in order to identify the device, monitor equipment ID and equipment name are also include in VB(variable bondings)."
            ::= { hwSiteAlarmTrapsPrefix 51 }

        hwRs485CommAlarmResumeTraps NOTIFICATION-TYPE
            OBJECTS { hwAlarmTrapOrdinalNumber,hwAlarmText,hwAlarmLevel,hwAlarmSigDesc,hwSiteName,hwSiteAdminAddr,hwNetIdentifier,hwSiteDescription,hwMonEquipId,hwMonEquipName,hwMonitorOperStatus            }
            STATUS current
            DESCRIPTION
                "RS485 communication alarm resume. Its correlation binding parameters:  Site ID, Site name, Site description, NE ID, Alarm name, Alarm single description, Alarm port description, Alarm severity, and Site alarm SN. Additionally, in order to identify the device, monitor equipment ID and equipment name are also include in VB(variable bondings)."
            ::= { hwSiteAlarmTrapsPrefix 52 }

        hwNetCommAlarmTraps NOTIFICATION-TYPE
            OBJECTS { hwAlarmTrapOrdinalNumber,hwAlarmText,hwAlarmLevel,hwAlarmSigDesc,hwSiteName,hwSiteAdminAddr,hwNetIdentifier,hwSiteDescription,hwMonEquipId,hwMonEquipName,hwMonitorOperStatus            }
            STATUS current
            DESCRIPTION
                "Network communication of monitors disconnect. Its correlation binding parameters:  Site ID, Site name, Site description, NE ID, Alarm name, Alarm single description, Alarm port description, Alarm severity, and Site alarm SN. Additionally, in order to identify the device, monitor equipment ID and equipment name are also include in VB(variable bondings)."
            ::= { hwSiteAlarmTrapsPrefix 53 }

        hwNetCommAlarmResumeTraps NOTIFICATION-TYPE
            OBJECTS { hwAlarmTrapOrdinalNumber,hwAlarmText,hwAlarmLevel,hwAlarmSigDesc,hwSiteName,hwSiteAdminAddr,hwNetIdentifier,hwSiteDescription,hwMonEquipId,hwMonEquipName,hwMonitorOperStatus            }
            STATUS current
            DESCRIPTION
                "Network communication alarm resume. Its correlation binding parameters:  Site ID, Site name, Site description, NE ID, Alarm name, Alarm single description, Alarm port description, Alarm severity, and Site alarm SN. Additionally, in order to identify the device, monitor equipment ID and equipment name are also include in VB(variable bondings)."
            ::= { hwSiteAlarmTrapsPrefix 54 }

        hwAcOffLongTimeAlarmTraps NOTIFICATION-TYPE
            OBJECTS { hwAlarmTrapOrdinalNumber,hwAlarmText,hwAlarmLevel,hwAlarmSigDesc,hwSiteName,hwSiteAdminAddr,hwNetIdentifier,hwSiteDescription,hwAcEquipId,hwAcEquipName,hwAcInputOperStatus            }
            STATUS current
            DESCRIPTION
                "AC power off for a long time alarms happened. Its correlation binding parameters:  Site ID, Site name, Site description, NE ID, Alarm name, Alarm single description, Alarm port description, Alarm severity, and Site alarm SN. Additionally, in order to identify the device, AC equipment ID and equipment name are also include in VB(variable bondings)."
            ::= { hwSiteAlarmTrapsPrefix 55 }

        hwAcOffLongTimeAlarmResumeTraps NOTIFICATION-TYPE
            OBJECTS { hwAlarmTrapOrdinalNumber,hwAlarmText,hwAlarmLevel,hwAlarmSigDesc,hwSiteName,hwSiteAdminAddr,hwNetIdentifier,hwSiteDescription,hwAcEquipId,hwAcEquipName,hwAcInputOperStatus            }
            STATUS current
            DESCRIPTION
                "AC power off for a long time alarms resume. Its correlation binding parameters:  Site ID, Site name, Site description, NE ID, Alarm name, Alarm single description, Alarm port description, Alarm severity, and Site alarm SN. Additionally, in order to identify the device, AC equipment ID and equipment name are also include in VB(variable bondings)."
            ::= { hwSiteAlarmTrapsPrefix 56 }

        hwSpdAlarmTraps NOTIFICATION-TYPE
            OBJECTS { hwAlarmTrapOrdinalNumber,hwAlarmText,hwAlarmLevel,hwAlarmSigDesc,hwSiteName,hwSiteAdminAddr,hwNetIdentifier,hwSiteDescription,hwAcEquipId,hwAcEquipName,hwAcFatherEquipname            }
            STATUS current
            DESCRIPTION
                "Description."
            ::= { hwSiteAlarmTrapsPrefix 57 }

        hwSpdAlarmResumeTraps NOTIFICATION-TYPE
            OBJECTS { hwAlarmTrapOrdinalNumber,hwAlarmText,hwAlarmLevel,hwAlarmSigDesc,hwSiteName,hwSiteAdminAddr,hwNetIdentifier,hwSiteDescription,hwAcEquipId,hwAcEquipName,hwAcFatherEquipname            }
            STATUS current
            DESCRIPTION
                "Description."
            ::= { hwSiteAlarmTrapsPrefix 58 }

        hwBadBatteryTraps NOTIFICATION-TYPE
            OBJECTS { hwAlarmTrapOrdinalNumber,hwAlarmText,hwAlarmLevel,hwAlarmSigDesc,hwSiteName,hwSiteAdminAddr,hwNetIdentifier,hwSiteDescription,hwBattsGroupId,hwBattsGroupName            }
            STATUS current
            DESCRIPTION
                "Description."
            ::= { hwSiteAlarmTrapsPrefix 59 }

        hwBadBatteryResumeTraps NOTIFICATION-TYPE
            OBJECTS { hwAlarmTrapOrdinalNumber,hwAlarmText,hwAlarmLevel,hwAlarmSigDesc,hwSiteName,hwSiteAdminAddr,hwNetIdentifier,hwSiteDescription,hwBattsGroupId,hwBattsGroupName            }
            STATUS current
            DESCRIPTION
                "Description."
            ::= { hwSiteAlarmTrapsPrefix 60 }

        hwLvd2DisconnectingTraps NOTIFICATION-TYPE
            OBJECTS { hwAlarmTrapOrdinalNumber,hwAlarmText,hwAlarmLevel,hwAlarmSigDesc,hwSiteName,hwSiteAdminAddr,hwNetIdentifier,hwSiteDescription,hwLvdUnitEquipId,hwLvdUnitEquipName,hwLvdBranchOperStatus            }
            STATUS current
            DESCRIPTION
                "Description."
            ::= { hwSiteAlarmTrapsPrefix 61 }

        hwLvd2DisconnectingResumeTraps NOTIFICATION-TYPE
            OBJECTS { hwAlarmTrapOrdinalNumber,hwAlarmText,hwAlarmLevel,hwAlarmSigDesc,hwSiteName,hwSiteAdminAddr,hwNetIdentifier,hwSiteDescription,hwLvdUnitEquipId,hwLvdUnitEquipName,hwLvdBranchOperStatus            }
            STATUS current
            DESCRIPTION
                "Description."
            ::= { hwSiteAlarmTrapsPrefix 62 }

        hwBattHighTempTraps NOTIFICATION-TYPE
            OBJECTS { hwAlarmTrapOrdinalNumber,hwAlarmText,hwAlarmLevel,hwAlarmSigDesc,hwSiteName,hwSiteAdminAddr,hwNetIdentifier,hwSiteDescription,hwBattStringEquipId,hwBattStringEquipName,hwBattStringOperStatus            }
            STATUS current
            DESCRIPTION
                "Description."
            ::= { hwSiteAlarmTrapsPrefix 63 }

        hwBattHighTempResumeTraps NOTIFICATION-TYPE
            OBJECTS { hwAlarmTrapOrdinalNumber,hwAlarmText,hwAlarmLevel,hwAlarmSigDesc,hwSiteName,hwSiteAdminAddr,hwNetIdentifier,hwSiteDescription,hwBattStringEquipId,hwBattStringEquipName,hwBattStringOperStatus            }
            STATUS current
            DESCRIPTION
                "Description."
            ::= { hwSiteAlarmTrapsPrefix 64 }

        hwBattLowTempTraps NOTIFICATION-TYPE
            OBJECTS { hwAlarmTrapOrdinalNumber,hwAlarmText,hwAlarmLevel,hwAlarmSigDesc,hwSiteName,hwSiteAdminAddr,hwNetIdentifier,hwSiteDescription,hwBattStringEquipId,hwBattStringEquipName,hwBattStringOperStatus            }
            STATUS current
            DESCRIPTION
                "Description."
            ::= { hwSiteAlarmTrapsPrefix 65 }

        hwBattLowTempResumeTraps NOTIFICATION-TYPE
            OBJECTS { hwAlarmTrapOrdinalNumber,hwAlarmText,hwAlarmLevel,hwAlarmSigDesc,hwSiteName,hwSiteAdminAddr,hwNetIdentifier,hwSiteDescription,hwBattStringEquipId,hwBattStringEquipName,hwBattStringOperStatus            }
            STATUS current
            DESCRIPTION
                "Description."
            ::= { hwSiteAlarmTrapsPrefix 66 }

        hwDcUltraOverVoltageTraps NOTIFICATION-TYPE
            OBJECTS { hwAlarmTrapOrdinalNumber,hwAlarmText,hwAlarmLevel,hwAlarmSigDesc,hwSiteName,hwSiteAdminAddr,hwNetIdentifier,hwSiteDescription,hwDcOutputEquipId,hwDcOutputEquipName,hwDcFatherEquipname,hwDcOutputOperStatus            }
            STATUS current
            DESCRIPTION
                "Description."
            ::= { hwSiteAlarmTrapsPrefix 67 }

        hwDcUltraOverVoltageResumeTraps NOTIFICATION-TYPE
            OBJECTS { hwAlarmTrapOrdinalNumber,hwAlarmText,hwAlarmLevel,hwAlarmSigDesc,hwSiteName,hwSiteAdminAddr,hwNetIdentifier,hwSiteDescription,hwDcOutputEquipId,hwDcOutputEquipName,hwDcFatherEquipname,hwDcOutputOperStatus            }
            STATUS current
            DESCRIPTION
                "Description."
            ::= { hwSiteAlarmTrapsPrefix 68 }

        hwDcUltraUnderVoltageTraps NOTIFICATION-TYPE
            OBJECTS { hwAlarmTrapOrdinalNumber,hwAlarmText,hwAlarmLevel,hwAlarmSigDesc,hwSiteName,hwSiteAdminAddr,hwNetIdentifier,hwSiteDescription,hwDcOutputEquipId,hwDcOutputEquipName,hwDcFatherEquipname,hwDcOutputOperStatus            }
            STATUS current
            DESCRIPTION
                "Description."
            ::= { hwSiteAlarmTrapsPrefix 69 }

        hwDcUltraUnderVoltageResumeTraps NOTIFICATION-TYPE
            OBJECTS { hwAlarmTrapOrdinalNumber,hwAlarmText,hwAlarmLevel,hwAlarmSigDesc,hwSiteName,hwSiteAdminAddr,hwNetIdentifier,hwSiteDescription,hwDcOutputEquipId,hwDcOutputEquipName,hwDcFatherEquipname,hwDcOutputOperStatus            }
            STATUS current
            DESCRIPTION
                "Description."
            ::= { hwSiteAlarmTrapsPrefix 70 }

        hwUmiCommFailTraps NOTIFICATION-TYPE
            OBJECTS { hwAlarmTrapOrdinalNumber,hwAlarmText,hwAlarmLevel,hwAlarmSigDesc,hwSiteName,hwSiteAdminAddr,hwNetIdentifier,hwSiteDescription,hwEnvUnitsGroupId,hwEnvUnitsGroupName            }
            STATUS current
            DESCRIPTION
                "Description."
            ::= { hwSiteAlarmTrapsPrefix 71 }

        hwUmiCommFailResumeTraps NOTIFICATION-TYPE
            OBJECTS { hwAlarmTrapOrdinalNumber,hwAlarmText,hwAlarmLevel,hwAlarmSigDesc,hwSiteName,hwSiteAdminAddr,hwNetIdentifier,hwSiteDescription,hwEnvUnitsGroupId,hwEnvUnitsGroupName            }
            STATUS current
            DESCRIPTION
                "Description."
            ::= { hwSiteAlarmTrapsPrefix 72 }

        hwShortTestFailTraps NOTIFICATION-TYPE
            OBJECTS { hwAlarmTrapOrdinalNumber,hwAlarmText,hwAlarmLevel,hwAlarmSigDesc,hwSiteName,hwSiteAdminAddr,hwNetIdentifier,hwSiteDescription,hwBattsGroupId,hwBattsGroupName            }
            STATUS current
            DESCRIPTION
                "Description."
            ::= { hwSiteAlarmTrapsPrefix 73 }

        hwShortTestFailResumeTraps NOTIFICATION-TYPE
            OBJECTS { hwAlarmTrapOrdinalNumber,hwAlarmText,hwAlarmLevel,hwAlarmSigDesc,hwSiteName,hwSiteAdminAddr,hwNetIdentifier,hwSiteDescription,hwBattsGroupId,hwBattsGroupName            }
            STATUS current
            DESCRIPTION
                "Description."
            ::= { hwSiteAlarmTrapsPrefix 74 }

        hwMissingBattTempSensorTraps NOTIFICATION-TYPE
            OBJECTS { hwAlarmTrapOrdinalNumber,hwAlarmText,hwAlarmLevel,hwAlarmSigDesc,hwSiteName,hwSiteAdminAddr,hwNetIdentifier,hwSiteDescription,hwBattsGroupId,hwBattsGroupName            }
            STATUS current
            DESCRIPTION
                "Description."
            ::= { hwSiteAlarmTrapsPrefix 75 }

        hwMissingBattTempSensorResumeTraps NOTIFICATION-TYPE
            OBJECTS { hwAlarmTrapOrdinalNumber,hwAlarmText,hwAlarmLevel,hwAlarmSigDesc,hwSiteName,hwSiteAdminAddr,hwNetIdentifier,hwSiteDescription,hwBattsGroupId,hwBattsGroupName            }
            STATUS current
            DESCRIPTION
                "Description."
            ::= { hwSiteAlarmTrapsPrefix 76 }

        hwBattTempSensorFaultTraps NOTIFICATION-TYPE
            OBJECTS { hwAlarmTrapOrdinalNumber,hwAlarmText,hwAlarmLevel,hwAlarmSigDesc,hwSiteName,hwSiteAdminAddr,hwNetIdentifier,hwSiteDescription,hwBattsGroupId,hwBattsGroupName            }
            STATUS current
            DESCRIPTION
                "Description."
            ::= { hwSiteAlarmTrapsPrefix 77 }

        hwBattTempSensorFaultResumeTraps NOTIFICATION-TYPE
            OBJECTS { hwAlarmTrapOrdinalNumber,hwAlarmText,hwAlarmLevel,hwAlarmSigDesc,hwSiteName,hwSiteAdminAddr,hwNetIdentifier,hwSiteDescription,hwBattsGroupId,hwBattsGroupName            }
            STATUS current
            DESCRIPTION
                "Description."
            ::= { hwSiteAlarmTrapsPrefix 78 }

        hwAcOverVoltageTraps NOTIFICATION-TYPE
            OBJECTS { hwAlarmTrapOrdinalNumber,hwAlarmText,hwAlarmLevel,hwAlarmSigDesc,hwSiteName,hwSiteAdminAddr,hwNetIdentifier,hwSiteDescription,hwAcEquipId,hwAcEquipName,hwAcFatherEquipname,hwAcInputOperStatus            }
            STATUS current
            DESCRIPTION
                "Description."
            ::= { hwSiteAlarmTrapsPrefix 79 }

        hwAcOverVoltageResumeTraps NOTIFICATION-TYPE
            OBJECTS { hwAlarmTrapOrdinalNumber,hwAlarmText,hwAlarmLevel,hwAlarmSigDesc,hwSiteName,hwSiteAdminAddr,hwNetIdentifier,hwSiteDescription,hwAcEquipId,hwAcEquipName,hwAcFatherEquipname,hwAcInputOperStatus            }
            STATUS current
            DESCRIPTION
                "Description."
            ::= { hwSiteAlarmTrapsPrefix 80 }

        hwAcUnderVoltageTraps NOTIFICATION-TYPE
            OBJECTS { hwAlarmTrapOrdinalNumber,hwAlarmText,hwAlarmLevel,hwAlarmSigDesc,hwSiteName,hwSiteAdminAddr,hwNetIdentifier,hwSiteDescription,hwAcEquipId,hwAcEquipName,hwAcFatherEquipname,hwAcInputOperStatus            }
            STATUS current
            DESCRIPTION
                "Description."
            ::= { hwSiteAlarmTrapsPrefix 81 }

        hwAcUnderVoltageResumeTraps NOTIFICATION-TYPE
            OBJECTS { hwAlarmTrapOrdinalNumber,hwAlarmText,hwAlarmLevel,hwAlarmSigDesc,hwSiteName,hwSiteAdminAddr,hwNetIdentifier,hwSiteDescription,hwAcEquipId,hwAcEquipName,hwAcFatherEquipname,hwAcInputOperStatus            }
            STATUS current
            DESCRIPTION
                "Description."
            ::= { hwSiteAlarmTrapsPrefix 82 }

        hwTcuFanAlarmTraps NOTIFICATION-TYPE
            OBJECTS { hwAlarmTrapOrdinalNumber,hwAlarmText,hwAlarmLevel,hwAlarmSigDesc,hwSiteName,hwSiteAdminAddr,hwNetIdentifier,hwSiteDescription,hwFanEquipId,hwFanEquipName,hwFanOperStatus            }
            STATUS current
            DESCRIPTION
                "Description."
            ::= { hwSiteAlarmTrapsPrefix 83 }

        hwTcuFanAlarmResumeTraps NOTIFICATION-TYPE
            OBJECTS { hwAlarmTrapOrdinalNumber,hwAlarmText,hwAlarmLevel,hwAlarmSigDesc,hwSiteName,hwSiteAdminAddr,hwNetIdentifier,hwSiteDescription,hwFanEquipId,hwFanEquipName,hwFanOperStatus            }
            STATUS current
            DESCRIPTION
                "Description."
            ::= { hwSiteAlarmTrapsPrefix 84 }

        hwTcuDcAirAlarmTraps NOTIFICATION-TYPE
            OBJECTS { hwAlarmTrapOrdinalNumber,hwAlarmText,hwAlarmLevel,hwAlarmSigDesc,hwSiteName,hwSiteAdminAddr,hwNetIdentifier,hwSiteDescription,hwDcAirEquipId,hwDcAirEquipName,hwDcAirOperStatus            }
            STATUS current
            DESCRIPTION
                "Description."
            ::= { hwSiteAlarmTrapsPrefix 85 }

        hwTcuDcAirAlarmResumeTraps NOTIFICATION-TYPE
            OBJECTS { hwAlarmTrapOrdinalNumber,hwAlarmText,hwAlarmLevel,hwAlarmSigDesc,hwSiteName,hwSiteAdminAddr,hwNetIdentifier,hwSiteDescription,hwDcAirEquipId,hwDcAirEquipName,hwDcAirOperStatus            }
            STATUS current
            DESCRIPTION
                "Description."
            ::= { hwSiteAlarmTrapsPrefix 86 }

        hwTripBreakAlarmTraps NOTIFICATION-TYPE
            OBJECTS { hwAlarmTrapOrdinalNumber,hwAlarmText,hwAlarmLevel,hwAlarmSigDesc,hwSiteName,hwSiteAdminAddr,hwNetIdentifier,hwSiteDescription,hwDcOutputEquipId,hwDcOutputEquipName,hwDcFatherEquipname            }
            STATUS current
            DESCRIPTION
                "Description."
            ::= { hwSiteAlarmTrapsPrefix 87 }

        hwTripBreakAlarmResumeTraps NOTIFICATION-TYPE
            OBJECTS { hwAlarmTrapOrdinalNumber,hwAlarmText,hwAlarmLevel,hwAlarmSigDesc,hwSiteName,hwSiteAdminAddr,hwNetIdentifier,hwSiteDescription,hwDcOutputEquipId,hwDcOutputEquipName,hwDcFatherEquipname            }
            STATUS current
            DESCRIPTION
                "Description."
            ::= { hwSiteAlarmTrapsPrefix 88 }

        hwTripBatteryCabinetAlarmTraps NOTIFICATION-TYPE
            OBJECTS { hwAlarmTrapOrdinalNumber,hwAlarmText,hwAlarmLevel,hwAlarmSigDesc,hwSiteName,hwSiteAdminAddr,hwNetIdentifier,hwSiteDescription,hwBatteryCabinetEquipId,hwBatteryCabinetEquipName            }
            STATUS current
            DESCRIPTION
                "Description."
            ::= { hwSiteAlarmTrapsPrefix 89 }

        hwTripBattCabAlarmResumeTraps NOTIFICATION-TYPE
            OBJECTS { hwAlarmTrapOrdinalNumber,hwAlarmText,hwAlarmLevel,hwAlarmSigDesc,hwSiteName,hwSiteAdminAddr,hwNetIdentifier,hwSiteDescription,hwBatteryCabinetEquipId,hwBatteryCabinetEquipName            }
            STATUS current
            DESCRIPTION
                "Description."
            ::= { hwSiteAlarmTrapsPrefix 90 }

        hwBattTestAlarmTraps NOTIFICATION-TYPE
            OBJECTS { hwAlarmTrapOrdinalNumber,hwAlarmText,hwAlarmLevel,hwAlarmSigDesc,hwSiteName,hwSiteAdminAddr,hwNetIdentifier,hwSiteDescription,hwBattsGroupId,hwBattsGroupName            }
            STATUS current
            DESCRIPTION
                "Description."
            ::= { hwSiteAlarmTrapsPrefix 103 }

        hwBattTestAlarmResumeTraps NOTIFICATION-TYPE
            OBJECTS { hwAlarmTrapOrdinalNumber,hwAlarmText,hwAlarmLevel,hwAlarmSigDesc,hwSiteName,hwSiteAdminAddr,hwNetIdentifier,hwSiteDescription,hwBattsGroupId,hwBattsGroupName            }
            STATUS current
            DESCRIPTION
                "Description."
            ::= { hwSiteAlarmTrapsPrefix 104 }

        hwBattContactorFaultTraps NOTIFICATION-TYPE
            OBJECTS { hwAlarmTrapOrdinalNumber,hwAlarmText,hwAlarmLevel,hwAlarmSigDesc,hwSiteName,hwSiteAdminAddr,hwNetIdentifier,hwSiteDescription,hwBattsGroupId,hwBattsGroupName            }
            STATUS current
            DESCRIPTION
                "Description."
            ::= { hwSiteAlarmTrapsPrefix 105 }

        hwBattContactorFaultResumeTraps NOTIFICATION-TYPE
            OBJECTS { hwAlarmTrapOrdinalNumber,hwAlarmText,hwAlarmLevel,hwAlarmSigDesc,hwSiteName,hwSiteAdminAddr,hwNetIdentifier,hwSiteDescription,hwBattsGroupId,hwBattsGroupName            }
            STATUS current
            DESCRIPTION
                "Description."
            ::= { hwSiteAlarmTrapsPrefix 106 }

        hwBattFuseBreakAlarmTraps NOTIFICATION-TYPE
            OBJECTS { hwAlarmTrapOrdinalNumber,hwAlarmText,hwAlarmLevel,hwAlarmSigDesc,hwSiteName,hwSiteAdminAddr,hwNetIdentifier,hwSiteDescription,hwBattStringEquipId,hwBattStringEquipName,hwBattStringOperStatus            }
            STATUS current
            DESCRIPTION
                "Description."
            ::= { hwSiteAlarmTrapsPrefix 107 }

        hwBattFuseBreakAlarmResumeTraps NOTIFICATION-TYPE
            OBJECTS { hwAlarmTrapOrdinalNumber,hwAlarmText,hwAlarmLevel,hwAlarmSigDesc,hwSiteName,hwSiteAdminAddr,hwNetIdentifier,hwSiteDescription,hwBattStringEquipId,hwBattStringEquipName,hwBattStringOperStatus            }
            STATUS current
            DESCRIPTION
                "Description."
            ::= { hwSiteAlarmTrapsPrefix 108 }

        hwDCDAbnormalAlarmTraps NOTIFICATION-TYPE
            OBJECTS { hwAlarmTrapOrdinalNumber,hwAlarmText,hwAlarmLevel,hwAlarmSigDesc,hwSiteName,hwSiteAdminAddr,hwNetIdentifier,hwSiteDescription,hwDcOutputEquipId,hwDcOutputEquipName,hwDcOutputOperStatus            }
            STATUS current
            DESCRIPTION
                "Description."
            ::= { hwSiteAlarmTrapsPrefix 109 }

        hwDCDAbnormalAlarmResumeTraps NOTIFICATION-TYPE
            OBJECTS { hwAlarmTrapOrdinalNumber,hwAlarmText,hwAlarmLevel,hwAlarmSigDesc,hwSiteName,hwSiteAdminAddr,hwNetIdentifier,hwSiteDescription,hwDcOutputEquipId,hwDcOutputEquipName,hwDcOutputOperStatus            }
            STATUS current
            DESCRIPTION
                "Description."
            ::= { hwSiteAlarmTrapsPrefix 110 }

        hwACDAbnormalAlarmTraps NOTIFICATION-TYPE
            OBJECTS { hwAlarmTrapOrdinalNumber,hwAlarmText,hwAlarmLevel,hwAlarmSigDesc,hwSiteName,hwSiteAdminAddr,hwNetIdentifier,hwSiteDescription,hwAcEquipId,hwAcEquipName,hwAcInputOperStatus            }
            STATUS current
            DESCRIPTION
                "Description."
            ::= { hwSiteAlarmTrapsPrefix 111 }

        hwACDAbnormalAlarmResumeTraps NOTIFICATION-TYPE
            OBJECTS { hwAlarmTrapOrdinalNumber,hwAlarmText,hwAlarmLevel,hwAlarmSigDesc,hwSiteName,hwSiteAdminAddr,hwNetIdentifier,hwSiteDescription,hwAcEquipId,hwAcEquipName,hwAcInputOperStatus            }
            STATUS current
            DESCRIPTION
                "Description."
            ::= { hwSiteAlarmTrapsPrefix 112 }

        hwLoadOverCurrentAlarmTraps NOTIFICATION-TYPE
            OBJECTS { hwAlarmTrapOrdinalNumber,hwAlarmText,hwAlarmLevel,hwAlarmSigDesc,hwSiteName,hwSiteAdminAddr,hwNetIdentifier,hwSiteDescription,hwDcOutputEquipId,hwDcOutputEquipName,hwDcFatherEquipname,hwDcOutputOperStatus            }
            STATUS current
            DESCRIPTION
                "Description."
            ::= { hwSiteAlarmTrapsPrefix 113 }

        hwLoadOverCurrentAlarmResumeTraps NOTIFICATION-TYPE
            OBJECTS { hwAlarmTrapOrdinalNumber,hwAlarmText,hwAlarmLevel,hwAlarmSigDesc,hwSiteName,hwSiteAdminAddr,hwNetIdentifier,hwSiteDescription,hwDcOutputEquipId,hwDcOutputEquipName,hwDcFatherEquipname,hwDcOutputOperStatus            }
            STATUS current
            DESCRIPTION
                "Description."
            ::= { hwSiteAlarmTrapsPrefix 114 }

        hwEOSNoResponseAlarmTraps NOTIFICATION-TYPE
            OBJECTS { hwAlarmTrapOrdinalNumber,hwAlarmText,hwAlarmLevel,hwAlarmSigDesc,hwSiteName,hwSiteAdminAddr,hwNetIdentifier,hwSiteDescription,hwLoadBranchEquipId,hwLoadBranchEquipName,hwLoadBranchOperStatus            }
            STATUS current
            DESCRIPTION
                "Description."
            ::= { hwSiteAlarmTrapsPrefix 115 }

        hwEOSNoResponseAlarmResumeTraps NOTIFICATION-TYPE
            OBJECTS { hwAlarmTrapOrdinalNumber,hwAlarmText,hwAlarmLevel,hwAlarmSigDesc,hwSiteName,hwSiteAdminAddr,hwNetIdentifier,hwSiteDescription,hwLoadBranchEquipId,hwLoadBranchEquipName,hwLoadBranchOperStatus            }
            STATUS current
            DESCRIPTION
                "Description."
            ::= { hwSiteAlarmTrapsPrefix 116 }

        hwEOSOverLoadAlarmTraps NOTIFICATION-TYPE
            OBJECTS { hwAlarmTrapOrdinalNumber,hwAlarmText,hwAlarmLevel,hwAlarmSigDesc,hwSiteName,hwSiteAdminAddr,hwNetIdentifier,hwSiteDescription,hwLoadBranchEquipId,hwLoadBranchEquipName,hwLoadBranchOperStatus            }
            STATUS current
            DESCRIPTION
                "Description."
            ::= { hwSiteAlarmTrapsPrefix 117 }

        hwEOSOverLoadAlarmResumeTraps NOTIFICATION-TYPE
            OBJECTS { hwAlarmTrapOrdinalNumber,hwAlarmText,hwAlarmLevel,hwAlarmSigDesc,hwSiteName,hwSiteAdminAddr,hwNetIdentifier,hwSiteDescription,hwLoadBranchEquipId,hwLoadBranchEquipName,hwLoadBranchOperStatus            }
            STATUS current
            DESCRIPTION
                "Description."
            ::= { hwSiteAlarmTrapsPrefix 118 }

        hwInverterAlarmTraps NOTIFICATION-TYPE
            OBJECTS { hwAlarmTrapOrdinalNumber,hwAlarmText,hwAlarmLevel,hwAlarmSigDesc,hwSiteName,hwSiteAdminAddr,hwNetIdentifier,hwSiteDescription,hwInverterEquipId,hwInverterEquipName,hwInverterOperStatus            }
            STATUS current
            DESCRIPTION
                "Description."
            ::= { hwSiteAlarmTrapsPrefix 119 }

        hwInveterAlarmResumeTraps NOTIFICATION-TYPE
            OBJECTS { hwAlarmTrapOrdinalNumber,hwAlarmText,hwAlarmLevel,hwAlarmSigDesc,hwSiteName,hwSiteAdminAddr,hwNetIdentifier,hwSiteDescription,hwInverterEquipId,hwInverterEquipName,hwInverterOperStatus            }
            STATUS current
            DESCRIPTION
                "Description."
            ::= { hwSiteAlarmTrapsPrefix 120 }

        hwDGAlarmTraps NOTIFICATION-TYPE
            OBJECTS { hwAlarmTrapOrdinalNumber,hwAlarmText,hwAlarmLevel,hwAlarmSigDesc,hwSiteName,hwSiteAdminAddr,hwNetIdentifier,hwSiteDescription,hwDGEquipId,hwDGEquipName            }
            STATUS current
            DESCRIPTION
                "Description."
            ::= { hwSiteAlarmTrapsPrefix 121 }

        hwDGAlarmResumeTraps NOTIFICATION-TYPE
            OBJECTS { hwAlarmTrapOrdinalNumber,hwAlarmText,hwAlarmLevel,hwAlarmSigDesc,hwSiteName,hwSiteAdminAddr,hwNetIdentifier,hwSiteDescription,hwDGEquipId,hwDGEquipName            }
            STATUS current
            DESCRIPTION
                "Description."
            ::= { hwSiteAlarmTrapsPrefix 122 }

        hwSSUSummaryAlarmTraps NOTIFICATION-TYPE
            OBJECTS { hwAlarmTrapOrdinalNumber,hwAlarmText,hwAlarmLevel,hwAlarmSigDesc,hwSiteName,hwSiteAdminAddr,hwNetIdentifier,hwSiteDescription,hwSSUGroupId,hwSSUGroupName            }
            STATUS current
            DESCRIPTION
                "Description."
            ::= { hwSiteAlarmTrapsPrefix 123 }

        hwSSUSummaryAlarmResumeTraps NOTIFICATION-TYPE
            OBJECTS { hwAlarmTrapOrdinalNumber,hwAlarmText,hwAlarmLevel,hwAlarmSigDesc,hwSiteName,hwSiteAdminAddr,hwNetIdentifier,hwSiteDescription,hwSSUGroupId,hwSSUGroupName            }
            STATUS current
            DESCRIPTION
                "Description."
            ::= { hwSiteAlarmTrapsPrefix 124 }

        hwSSUAlarmTraps NOTIFICATION-TYPE
            OBJECTS { hwAlarmTrapOrdinalNumber,hwAlarmText,hwAlarmLevel,hwAlarmSigDesc,hwSiteName,hwSiteAdminAddr,hwNetIdentifier,hwSiteDescription,hwSSUEquipId,hwSSUEquipName            }
            STATUS current
            DESCRIPTION
                "Description."
            ::= { hwSiteAlarmTrapsPrefix 125 }

        hwSSUAlarmResumeTraps NOTIFICATION-TYPE
            OBJECTS { hwAlarmTrapOrdinalNumber,hwAlarmText,hwAlarmLevel,hwAlarmSigDesc,hwSiteName,hwSiteAdminAddr,hwNetIdentifier,hwSiteDescription,hwSSUEquipId,hwSSUEquipName            }
            STATUS current
            DESCRIPTION
                "Description."
            ::= { hwSiteAlarmTrapsPrefix 126 }

        hwTemp1SensorAlarmTraps NOTIFICATION-TYPE
            OBJECTS { hwAlarmTrapOrdinalNumber,hwAlarmText,hwAlarmLevel,hwAlarmSigDesc,hwSiteName,hwSiteAdminAddr,hwNetIdentifier,hwSiteDescription,hwDeviceUimEquipId,hwDeviceUimEquipName,hwDeviceUimFatherEquipname            }
            STATUS current
            DESCRIPTION
                "Description."
            ::= { hwSiteAlarmTrapsPrefix 127 }

        hwTemp1SensorAlarmResumeTraps NOTIFICATION-TYPE
            OBJECTS { hwAlarmTrapOrdinalNumber,hwAlarmText,hwAlarmLevel,hwAlarmSigDesc,hwSiteName,hwSiteAdminAddr,hwNetIdentifier,hwSiteDescription,hwDeviceUimEquipId,hwDeviceUimEquipName,hwDeviceUimFatherEquipname            }
            STATUS current
            DESCRIPTION
                "Description."
            ::= { hwSiteAlarmTrapsPrefix 128 }

        hwTemp2SensorAlarmTraps NOTIFICATION-TYPE
            OBJECTS { hwAlarmTrapOrdinalNumber,hwAlarmText,hwAlarmLevel,hwAlarmSigDesc,hwSiteName,hwSiteAdminAddr,hwNetIdentifier,hwSiteDescription,hwDeviceUimEquipId,hwDeviceUimEquipName,hwDeviceUimFatherEquipname            }
            STATUS current
            DESCRIPTION
                "Description."
            ::= { hwSiteAlarmTrapsPrefix 129 }

        hwTemp2SensorAlarmResumeTraps NOTIFICATION-TYPE
            OBJECTS { hwAlarmTrapOrdinalNumber,hwAlarmText,hwAlarmLevel,hwAlarmSigDesc,hwSiteName,hwSiteAdminAddr,hwNetIdentifier,hwSiteDescription,hwDeviceUimEquipId,hwDeviceUimEquipName,hwDeviceUimFatherEquipname            }
            STATUS current
            DESCRIPTION
                "Description."
            ::= { hwSiteAlarmTrapsPrefix 130 }

        hwEsduDigitalInputAlarmTraps NOTIFICATION-TYPE
            OBJECTS { hwAlarmTrapOrdinalNumber,hwAlarmText,hwAlarmLevel,hwAlarmSigDesc,hwSiteName,hwSiteAdminAddr,hwNetIdentifier,hwSiteDescription,hwEsduEquipId,hwEsduEquipName            }
            STATUS current
            DESCRIPTION
                "The ESDU Spare digital fault. Its correlation binding parameters:  Site ID, Site name, Site description, NE ID, Alarm name, Alarm single description, Alarm port description, Alarm severity, and Site alarm SN. Additionally, in order to identify the device, Spare digital equipment ID and equipment name are also include in VB(variable bondings).    "
            ::= { hwSiteAlarmTrapsPrefix 147 }

        hwEsduDigitalInputAlarmResumeTraps NOTIFICATION-TYPE
            OBJECTS { hwAlarmTrapOrdinalNumber,hwAlarmText,hwAlarmLevel,hwAlarmSigDesc,hwSiteName,hwSiteAdminAddr,hwNetIdentifier,hwSiteDescription,hwEsduEquipId,hwEsduEquipName            }
            STATUS current
            DESCRIPTION
                "The ESDU Spare digital alarm resume.Its correlation binding parameters:  Site ID, Site name, Site description, NE ID, Alarm name, Alarm single description, Alarm port description, Alarm severity, and Site alarm SN. Additionally, in order to identify the device, Spare digital equipment ID and equipment name are also include in VB(variable bondings).    "
            ::= { hwSiteAlarmTrapsPrefix 148 }

        hwEsduDoorOpenAlarmTraps NOTIFICATION-TYPE
            OBJECTS { hwAlarmTrapOrdinalNumber,hwAlarmText,hwAlarmLevel,hwAlarmSigDesc,hwSiteName,hwSiteAdminAddr,hwNetIdentifier,hwSiteDescription,hwEsduEquipId,hwEsduEquipName            }
            STATUS current
            DESCRIPTION
                "The ESDU door is open."
            ::= { hwSiteAlarmTrapsPrefix 149 }

        hwEsduDoorOpenAlarmResumeTraps NOTIFICATION-TYPE
            OBJECTS { hwAlarmTrapOrdinalNumber,hwAlarmText,hwAlarmLevel,hwAlarmSigDesc,hwSiteName,hwSiteAdminAddr,hwNetIdentifier,hwSiteDescription,hwEsduEquipId,hwEsduEquipName            }
            STATUS current
            DESCRIPTION
                "The ESDU door open  alarm resumed."
            ::= { hwSiteAlarmTrapsPrefix 150 }

        hwEsduTemp1SensorFaultAlarmTraps NOTIFICATION-TYPE
            OBJECTS { hwAlarmTrapOrdinalNumber,hwAlarmText,hwAlarmLevel,hwAlarmSigDesc,hwSiteName,hwSiteAdminAddr,hwNetIdentifier,hwSiteDescription,hwEsduEquipId,hwEsduEquipName,hwEsduTemp1OperStatus            }
            STATUS current
            DESCRIPTION
                "The ESDU TEMP1 sensor is faulty."
            ::= { hwSiteAlarmTrapsPrefix 151 }

        hwEsduTemp1SensorFaultAlarmResumeTraps NOTIFICATION-TYPE
            OBJECTS { hwAlarmTrapOrdinalNumber,hwAlarmText,hwAlarmLevel,hwAlarmSigDesc,hwSiteName,hwSiteAdminAddr,hwNetIdentifier,hwSiteDescription,hwEsduEquipId,hwEsduEquipName,hwEsduTemp1OperStatus            }
            STATUS current
            DESCRIPTION
                "The ESDU TEMP1 sensor fault alarm recovers."
            ::= { hwSiteAlarmTrapsPrefix 152 }

        hwEsduTemp1SensorMissAlarmTraps NOTIFICATION-TYPE
            OBJECTS { hwAlarmTrapOrdinalNumber,hwAlarmText,hwAlarmLevel,hwAlarmSigDesc,hwSiteName,hwSiteAdminAddr,hwNetIdentifier,hwSiteDescription,hwEsduEquipId,hwEsduEquipName,hwEsduTemp1OperStatus            }
            STATUS current
            DESCRIPTION
                "The ESDU TEMP1 sensor is missing."
            ::= { hwSiteAlarmTrapsPrefix 153 }

        hwEsduTemp1SensorMissAlarmResumeTraps NOTIFICATION-TYPE
            OBJECTS { hwAlarmTrapOrdinalNumber,hwAlarmText,hwAlarmLevel,hwAlarmSigDesc,hwSiteName,hwSiteAdminAddr,hwNetIdentifier,hwSiteDescription,hwEsduEquipId,hwEsduEquipName,hwEsduTemp1OperStatus            }
            STATUS current
            DESCRIPTION
                "The ESDU TEMP1 sensor missing alarm recovers."
            ::= { hwSiteAlarmTrapsPrefix 154 }

        hwEsduTemp2SensorFaultAlarmTraps NOTIFICATION-TYPE
            OBJECTS { hwAlarmTrapOrdinalNumber,hwAlarmText,hwAlarmLevel,hwAlarmSigDesc,hwSiteName,hwSiteAdminAddr,hwNetIdentifier,hwSiteDescription,hwEsduEquipId,hwEsduEquipName,hwEsduTemp1OperStatus            }
            STATUS current
            DESCRIPTION
                "The ESDU TEMP2 sensor is faulty."
            ::= { hwSiteAlarmTrapsPrefix 155 }

        hwEsduTemp2SensorFaultAlarmResumeTraps NOTIFICATION-TYPE
            OBJECTS { hwAlarmTrapOrdinalNumber,hwAlarmText,hwAlarmLevel,hwAlarmSigDesc,hwSiteName,hwSiteAdminAddr,hwNetIdentifier,hwSiteDescription,hwEsduEquipId,hwEsduEquipName,hwEsduTemp2OperStatus            }
            STATUS current
            DESCRIPTION
                "The ESDU TEMP2 sensor fault alarm recovers."
            ::= { hwSiteAlarmTrapsPrefix 156 }

        hwEsduTemp2SensorMissAlarmTraps NOTIFICATION-TYPE
            OBJECTS { hwAlarmTrapOrdinalNumber,hwAlarmText,hwAlarmLevel,hwAlarmSigDesc,hwSiteName,hwSiteAdminAddr,hwNetIdentifier,hwSiteDescription,hwEsduEquipId,hwEsduEquipName,hwEsduTemp2OperStatus            }
            STATUS current
            DESCRIPTION
                "The ESDU TEMP2 sensor is missing."
            ::= { hwSiteAlarmTrapsPrefix 157 }

        hwEsduTemp2SensorMissAlarmResumeTraps NOTIFICATION-TYPE
            OBJECTS { hwAlarmTrapOrdinalNumber,hwAlarmText,hwAlarmLevel,hwAlarmSigDesc,hwSiteName,hwSiteAdminAddr,hwNetIdentifier,hwSiteDescription,hwEsduEquipId,hwEsduEquipName,hwEsduTemp2OperStatus            }
            STATUS current
            DESCRIPTION
                "The ESDU TEMP2 sensor missing alarm recovers."
            ::= { hwSiteAlarmTrapsPrefix 158 }

        hwEsduBtempSensorFaultAlarmTraps NOTIFICATION-TYPE
            OBJECTS { hwAlarmTrapOrdinalNumber,hwAlarmText,hwAlarmLevel,hwAlarmSigDesc,hwSiteName,hwSiteAdminAddr,hwNetIdentifier,hwSiteDescription,hwEsduEquipId,hwEsduEquipName,hwEsduBtempOperStatus            }
            STATUS current
            DESCRIPTION
                "The ESDU BTEMP sensor is faulty."
            ::= { hwSiteAlarmTrapsPrefix 159 }

        hwEsduBtempSensorFaultAlarmResumeTraps NOTIFICATION-TYPE
            OBJECTS { hwAlarmTrapOrdinalNumber,hwAlarmText,hwAlarmLevel,hwAlarmSigDesc,hwSiteName,hwSiteAdminAddr,hwNetIdentifier,hwSiteDescription,hwEsduEquipId,hwEsduEquipName,hwEsduBtempOperStatus            }
            STATUS current
            DESCRIPTION
                "The ESDU BTEMP sensor fault alarm recovers."
            ::= { hwSiteAlarmTrapsPrefix 160 }

        hwEsduBtempSensorMissAlarmTraps NOTIFICATION-TYPE
            OBJECTS { hwAlarmTrapOrdinalNumber,hwAlarmText,hwAlarmLevel,hwAlarmSigDesc,hwSiteName,hwSiteAdminAddr,hwNetIdentifier,hwSiteDescription,hwEsduEquipId,hwEsduEquipName,hwEsduBtempOperStatus            }
            STATUS current
            DESCRIPTION
                "The ESDU BTEMP sensor is missing."
            ::= { hwSiteAlarmTrapsPrefix 161 }

        hwEsduBtempSensorMissAlarmResumeTraps NOTIFICATION-TYPE
            OBJECTS { hwAlarmTrapOrdinalNumber,hwAlarmText,hwAlarmLevel,hwAlarmSigDesc,hwSiteName,hwSiteAdminAddr,hwNetIdentifier,hwSiteDescription,hwEsduEquipId,hwEsduEquipName,hwEsduBtempOperStatus            }
            STATUS current
            DESCRIPTION
                "The ESDU BTEMP sensor missing alarm recovers."
            ::= { hwSiteAlarmTrapsPrefix 162 }

        hwEsduTemp1AlarmTraps NOTIFICATION-TYPE
            OBJECTS { hwAlarmTrapOrdinalNumber,hwAlarmText,hwAlarmLevel,hwAlarmSigDesc,hwSiteName,hwSiteAdminAddr,hwNetIdentifier,hwSiteDescription,hwEsduEquipId,hwEsduEquipName,hwEsduTemp1OperStatus            }
            STATUS current
            DESCRIPTION
                "The ESDU TEMP1 temperature is out of range（too high or too low）. "
            ::= { hwSiteAlarmTrapsPrefix 163 }

        hwEsduTemp1AlarmResumeTraps NOTIFICATION-TYPE
            OBJECTS { hwAlarmTrapOrdinalNumber,hwAlarmText,hwAlarmLevel,hwAlarmSigDesc,hwSiteName,hwSiteAdminAddr,hwNetIdentifier,hwSiteDescription,hwEsduEquipId,hwEsduEquipName,hwEsduTemp1OperStatus            }
            STATUS current
            DESCRIPTION
                "The ESDU TEMP1 temperature alarm resume.   "
            ::= { hwSiteAlarmTrapsPrefix 164 }

        hwEsduTemp2AlarmTraps NOTIFICATION-TYPE
            OBJECTS { hwAlarmTrapOrdinalNumber,hwAlarmText,hwAlarmLevel,hwAlarmSigDesc,hwSiteName,hwSiteAdminAddr,hwNetIdentifier,hwSiteDescription,hwEsduEquipId,hwEsduEquipName,hwEsduTemp2OperStatus            }
            STATUS current
            DESCRIPTION
                "The ESDU TEMP2 temperature is out of range（too high or too low）. "
            ::= { hwSiteAlarmTrapsPrefix 165 }

        hwEsduTemp2AlarmResumeTraps NOTIFICATION-TYPE
            OBJECTS { hwAlarmTrapOrdinalNumber,hwAlarmText,hwAlarmLevel,hwAlarmSigDesc,hwSiteName,hwSiteAdminAddr,hwNetIdentifier,hwSiteDescription,hwEsduEquipId,hwEsduEquipName,hwEsduTemp2OperStatus            }
            STATUS current
            DESCRIPTION
                "The ESDU TEMP2 temperature alarm resume.   "
            ::= { hwSiteAlarmTrapsPrefix 166 }

        hwEsduCommAlarmTraps NOTIFICATION-TYPE
            OBJECTS { hwAlarmTrapOrdinalNumber,hwAlarmText,hwAlarmLevel,hwAlarmSigDesc,hwSiteName,hwSiteAdminAddr,hwNetIdentifier,hwSiteDescription,hwEsduEquipId,hwEsduEquipName            }
            STATUS current
            DESCRIPTION
                "The Moniter cannot commuicate with the ESDU."
            ::= { hwSiteAlarmTrapsPrefix 167 }

        hwEsduCommAlarmResumeTraps NOTIFICATION-TYPE
            OBJECTS { hwAlarmTrapOrdinalNumber,hwAlarmText,hwAlarmLevel,hwAlarmSigDesc,hwSiteName,hwSiteAdminAddr,hwNetIdentifier,hwSiteDescription,hwEsduEquipId,hwEsduEquipName            }
            STATUS current
            DESCRIPTION
                "The communication between monitor and ESDU recovers."
            ::= { hwSiteAlarmTrapsPrefix 168 }

        hwBatteryLowCapacityAlarmTraps NOTIFICATION-TYPE
            OBJECTS { hwAlarmTrapOrdinalNumber,hwAlarmText,hwAlarmLevel,hwAlarmSigDesc,hwSiteName,hwSiteAdminAddr,hwNetIdentifier,hwSiteDescription,hwBattsGroupId,hwBattsGroupName            }
            STATUS current
            DESCRIPTION
                "The capacity of batteries is low."
            ::= { hwSiteAlarmTrapsPrefix 169 }

        hwBatteryLowCapacityAlarmResumeTraps NOTIFICATION-TYPE
            OBJECTS { hwAlarmTrapOrdinalNumber,hwAlarmText,hwAlarmLevel,hwAlarmSigDesc,hwSiteName,hwSiteAdminAddr,hwNetIdentifier,hwSiteDescription,hwBattsGroupId,hwBattsGroupName            }
            STATUS current
            DESCRIPTION
                "The alarm of low capacity resumed."
            ::= { hwSiteAlarmTrapsPrefix 170 }

        hwBatteryLostAlarmTraps NOTIFICATION-TYPE
            OBJECTS { hwAlarmTrapOrdinalNumber,hwAlarmText,hwAlarmLevel,hwAlarmSigDesc,hwSiteName,hwSiteAdminAddr,hwNetIdentifier,hwSiteDescription,hwBattStringEquipId,hwBattStringEquipName,hwBattStringFatherEquipname            }
            STATUS current
            DESCRIPTION
                "Some battery strings could be lost, when the alarm happened."
            ::= { hwSiteAlarmTrapsPrefix 171 }

        hwBatteryLostAlarmResumeTraps NOTIFICATION-TYPE
            OBJECTS { hwAlarmTrapOrdinalNumber,hwAlarmText,hwAlarmLevel,hwAlarmSigDesc,hwSiteName,hwSiteAdminAddr,hwNetIdentifier,hwSiteDescription,hwBattStringEquipId,hwBattStringEquipName,hwBattStringFatherEquipname            }
            STATUS current
            DESCRIPTION
                "If all the battery strings can be detected, the alarm of battery losting resume."
            ::= { hwSiteAlarmTrapsPrefix 172 }

        hwRectCapacityAlarmTraps NOTIFICATION-TYPE
            OBJECTS { hwAlarmTrapOrdinalNumber,hwAlarmText,hwAlarmLevel,hwAlarmSigDesc,hwSiteName,hwSiteAdminAddr,hwNetIdentifier,hwSiteDescription,hwRectsGroupId,hwRectsGroupName            }
            STATUS current
            DESCRIPTION
                "Low Rectifier Capacity or High Rectifier Capacity Alarm happened."
            ::= { hwSiteAlarmTrapsPrefix 131 }

        hwRectCapacityAlarmResumeTraps NOTIFICATION-TYPE
            OBJECTS { hwAlarmTrapOrdinalNumber,hwAlarmText,hwAlarmLevel,hwAlarmSigDesc,hwSiteName,hwSiteAdminAddr,hwNetIdentifier,hwSiteDescription,hwRectsGroupId,hwRectsGroupName            }
            STATUS current
            DESCRIPTION
                "Low Rectifier Capacity or High Rectifier Capacity Alarm Resumed."
            ::= { hwSiteAlarmTrapsPrefix 132 }

        hwPvLostAlarmTraps NOTIFICATION-TYPE
            OBJECTS { hwAlarmTrapOrdinalNumber,hwAlarmText,hwAlarmLevel,hwAlarmSigDesc,hwSiteName,hwSiteAdminAddr,hwNetIdentifier,hwSiteDescription            }
            STATUS current
            DESCRIPTION
                ""
            ::= { hwSiteAlarmTrapsPrefix 181 }

        hwPvLostAlarmResumeTraps NOTIFICATION-TYPE
            OBJECTS { hwAlarmTrapOrdinalNumber,hwAlarmText,hwAlarmLevel,hwAlarmSigDesc,hwSiteName,hwSiteAdminAddr,hwNetIdentifier,hwSiteDescription            }
            STATUS current
            DESCRIPTION
                ""
            ::= { hwSiteAlarmTrapsPrefix 182 }

        hwTcucTempSensorFaultAlarmTraps NOTIFICATION-TYPE
            OBJECTS { hwAlarmTrapOrdinalNumber,hwAlarmText,hwAlarmLevel,hwAlarmSigDesc,hwSiteName,hwSiteAdminAddr,hwNetIdentifier,hwSiteDescription            }
            STATUS current
            DESCRIPTION
                "The TCUC cabient temperature sensor fault alarm happened."
            ::= { hwSiteAlarmTrapsPrefix 133 }

        hwTcucTempSensorFaultAlarmResumeTraps NOTIFICATION-TYPE
            OBJECTS { hwAlarmTrapOrdinalNumber,hwAlarmText,hwAlarmLevel,hwAlarmSigDesc,hwSiteName,hwSiteAdminAddr,hwNetIdentifier,hwSiteDescription            }
            STATUS current
            DESCRIPTION
                "The TCUC cabient temperature sensor fault alarm resumed."
            ::= { hwSiteAlarmTrapsPrefix 134 }

        hwTcucFanFaultAlarmTraps NOTIFICATION-TYPE
            OBJECTS { hwAlarmTrapOrdinalNumber,hwAlarmText,hwAlarmLevel,hwAlarmSigDesc,hwSiteName,hwSiteAdminAddr,hwNetIdentifier,hwSiteDescription            }
            STATUS current
            DESCRIPTION
                "The TCUC cabient fan fault alarm happened."
            ::= { hwSiteAlarmTrapsPrefix 135 }

        hwTcucFanFaultAlarmResumeTraps NOTIFICATION-TYPE
            OBJECTS { hwAlarmTrapOrdinalNumber,hwAlarmText,hwAlarmLevel,hwAlarmSigDesc,hwSiteName,hwSiteAdminAddr,hwNetIdentifier,hwSiteDescription            }
            STATUS current
            DESCRIPTION
                "The TCUC cabient fan fault alarm resumed."
            ::= { hwSiteAlarmTrapsPrefix 136 }

        hwTcucTempAbnormalAlarmTraps NOTIFICATION-TYPE
            OBJECTS { hwAlarmTrapOrdinalNumber,hwAlarmText,hwAlarmLevel,hwAlarmSigDesc,hwSiteName,hwSiteAdminAddr,hwNetIdentifier,hwSiteDescription            }
            STATUS current
            DESCRIPTION
                "The TCUC cabinet temperature is too high or too low"
            ::= { hwSiteAlarmTrapsPrefix 137 }

        hwTcucTempAbnormalAlarmResumeTraps NOTIFICATION-TYPE
            OBJECTS { hwAlarmTrapOrdinalNumber,hwAlarmText,hwAlarmLevel,hwAlarmSigDesc,hwSiteName,hwSiteAdminAddr,hwNetIdentifier,hwSiteDescription            }
            STATUS current
            DESCRIPTION
                "The TCUC cabinet temperature abnormal alarm resumed."
            ::= { hwSiteAlarmTrapsPrefix 138 }

        hwTcucDoorOpenAlarmTraps NOTIFICATION-TYPE
            OBJECTS { hwAlarmTrapOrdinalNumber,hwAlarmText,hwAlarmLevel,hwAlarmSigDesc,hwSiteName,hwSiteAdminAddr,hwNetIdentifier,hwSiteDescription            }
            STATUS current
            DESCRIPTION
                "The TCUC cabinet door is open."
            ::= { hwSiteAlarmTrapsPrefix 139 }

        hwTcucDoorOpenAlarmResumeTraps NOTIFICATION-TYPE
            OBJECTS { hwAlarmTrapOrdinalNumber,hwAlarmText,hwAlarmLevel,hwAlarmSigDesc,hwSiteName,hwSiteAdminAddr,hwNetIdentifier,hwSiteDescription            }
            STATUS current
            DESCRIPTION
                "The TCUC cabient door open  alarm resumed."
            ::= { hwSiteAlarmTrapsPrefix 140 }

        hwTcucSmokeAlarmTraps NOTIFICATION-TYPE
            OBJECTS { hwAlarmTrapOrdinalNumber,hwAlarmText,hwAlarmLevel,hwAlarmSigDesc,hwSiteName,hwSiteAdminAddr,hwNetIdentifier,hwSiteDescription            }
            STATUS current
            DESCRIPTION
                "The TCUC cabient smoke alarm happened."
            ::= { hwSiteAlarmTrapsPrefix 141 }

        hwTcucSmokeAlarmResumeTraps NOTIFICATION-TYPE
            OBJECTS { hwAlarmTrapOrdinalNumber,hwAlarmText,hwAlarmLevel,hwAlarmSigDesc,hwSiteName,hwSiteAdminAddr,hwNetIdentifier,hwSiteDescription            }
            STATUS current
            DESCRIPTION
                "The TCUC cabient smoke alarm resumed"
            ::= { hwSiteAlarmTrapsPrefix 142 }

        hwTcucWaterAlarmTraps NOTIFICATION-TYPE
            OBJECTS { hwAlarmTrapOrdinalNumber,hwAlarmText,hwAlarmLevel,hwAlarmSigDesc,hwSiteName,hwSiteAdminAddr,hwNetIdentifier,hwSiteDescription            }
            STATUS current
            DESCRIPTION
                "The TCUC cabient water alarm happend."
            ::= { hwSiteAlarmTrapsPrefix 143 }

        hwTcucWaterAlarmResumeTraps NOTIFICATION-TYPE
            OBJECTS { hwAlarmTrapOrdinalNumber,hwAlarmText,hwAlarmLevel,hwAlarmSigDesc,hwSiteName,hwSiteAdminAddr,hwNetIdentifier,hwSiteDescription            }
            STATUS current
            DESCRIPTION
                "The TCUC cabient water alarm resumed."
            ::= { hwSiteAlarmTrapsPrefix 144 }

        hwTcucCommFailAlarmTraps NOTIFICATION-TYPE
            OBJECTS { hwAlarmTrapOrdinalNumber,hwAlarmText,hwAlarmLevel,hwAlarmSigDesc,hwSiteName,hwSiteAdminAddr,hwNetIdentifier,hwSiteDescription            }
            STATUS current
            DESCRIPTION
                "The TCUC cabient  failed communicate with the monitor."
            ::= { hwSiteAlarmTrapsPrefix 145 }

        hwTcucCommFailAlarmResumeTraps NOTIFICATION-TYPE
            OBJECTS { hwAlarmTrapOrdinalNumber,hwAlarmText,hwAlarmLevel,hwAlarmSigDesc,hwSiteName,hwSiteAdminAddr,hwNetIdentifier,hwSiteDescription            }
            STATUS current
            DESCRIPTION
                "The TCUC cabient  communication fail alarm resumed."
            ::= { hwSiteAlarmTrapsPrefix 146 }

        hwAtsAlarmTrap NOTIFICATION-TYPE
            OBJECTS { hwAlarmTrapOrdinalNumber,hwAlarmText,hwAlarmLevel,hwAlarmSigDesc,hwSiteName,hwSiteAdminAddr,hwNetIdentifier,hwSiteDescription,hwAtsEquipId,hwAtsEquipName            }
            STATUS current
            DESCRIPTION
                "ATS Alarm. Its correlation binding parameters:  Site ID, Site name, Site description, NE ID, Alarm name, Alarm single description, Alarm port description, Alarm severity, and Site alarm SN. Additionally, in order to identify the device, Spare digital equipment ID and equipment name are also include in VB(variable bondings)."
            ::= { hwSiteAlarmTrapsPrefix 187 }

        hwAtsAlarmResumeTrap NOTIFICATION-TYPE
            OBJECTS { hwAlarmTrapOrdinalNumber,hwAlarmText,hwAlarmLevel,hwAlarmSigDesc,hwSiteName,hwSiteAdminAddr,hwNetIdentifier,hwSiteDescription,hwAtsEquipId,hwAtsEquipName            }
            STATUS current
            DESCRIPTION
                "ATS Alarm Resume. Its correlation binding parameters:  Site ID, Site name, Site description, NE ID, Alarm name, Alarm single description, Alarm port description, Alarm severity, and Site alarm SN. Additionally, in order to identify the device, Spare digital equipment ID and equipment name are also include in VB(variable bondings)."
            ::= { hwSiteAlarmTrapsPrefix 188 }

        hwInverterTrapTable OBJECT IDENTIFIER ::= { hwSiteAlarmTraps 4 }

        hwInverterTrapPrefix OBJECT IDENTIFIER ::= { hwInverterTrapTable 0 }

        hwInverterCommFailAlarmTrap NOTIFICATION-TYPE
            OBJECTS { hwAlarmTrapOrdinalNumber,hwAlarmText,hwAlarmLevel,hwAlarmSigDesc,hwSiteName,hwSiteAdminAddr,hwNetIdentifier,hwSiteDescription,hwInverterEquipId,hwInverterEquipName            }
            STATUS current
            DESCRIPTION
                "Communication Failure.
                Its correlation binding parameters: 
                Site alarm serial number (SN),
                Alarm name,
                Alarm level,
                Site name,
                Site administrant address,
                NE ID,
                Site description,
                Additionally, in order to identify the device, rectifier equipment ID and equipment name are also include in VB(variable bondings)."
            ::= { hwInverterTrapPrefix 1 }

        hwInverterCommFailAlarmResumeTrap NOTIFICATION-TYPE
            OBJECTS { hwAlarmTrapOrdinalNumber,hwAlarmText,hwAlarmLevel,hwAlarmSigDesc,hwSiteName,hwSiteAdminAddr,hwNetIdentifier,hwSiteDescription,hwInverterEquipId,hwInverterEquipName            }
            STATUS current
            DESCRIPTION
                "Communication Failure Resume.
                Its correlation binding parameters: 
                Site alarm serial number (SN),
                Alarm name,
                Alarm level,
                Site name,
                Site administrant address,
                NE ID,
                Site description,
                Additionally, in order to identify the device, rectifier equipment ID and equipment name are also include in VB(variable bondings)."
            ::= { hwInverterTrapPrefix 2 }

        hwInverterFanFaultAlarmTrap NOTIFICATION-TYPE
            OBJECTS { hwAlarmTrapOrdinalNumber,hwAlarmText,hwAlarmLevel,hwAlarmSigDesc,hwSiteName,hwSiteAdminAddr,hwNetIdentifier,hwSiteDescription,hwInverterEquipId,hwInverterEquipName            }
            STATUS current
            DESCRIPTION
                "Fan Failure.
                Its correlation binding parameters: 
                Site alarm serial number (SN),
                Alarm name,
                Alarm level,
                Site name,
                Site administrant address,
                NE ID,
                Site description,
                Additionally, in order to identify the device, rectifier equipment ID and equipment name are also include in VB(variable bondings)."
            ::= { hwInverterTrapPrefix 3 }

        hwInverterFanFaultAlarmResumeTrap NOTIFICATION-TYPE
            OBJECTS { hwAlarmTrapOrdinalNumber,hwAlarmText,hwAlarmLevel,hwAlarmSigDesc,hwSiteName,hwSiteAdminAddr,hwNetIdentifier,hwSiteDescription,hwInverterEquipId,hwInverterEquipName            }
            STATUS current
            DESCRIPTION
                "Fan Failure Resume.
                Its correlation binding parameters: 
                Site alarm serial number (SN),
                Alarm name,
                Alarm level,
                Site name,
                Site administrant address,
                NE ID,
                Site description,
                Additionally, in order to identify the device, rectifier equipment ID and equipment name are also include in VB(variable bondings)."
            ::= { hwInverterTrapPrefix 4 }

        hwInverterACOutLowAlarmTrap NOTIFICATION-TYPE
            OBJECTS { hwAlarmTrapOrdinalNumber,hwAlarmText,hwAlarmLevel,hwAlarmSigDesc,hwSiteName,hwSiteAdminAddr,hwNetIdentifier,hwSiteDescription,hwInverterEquipId,hwInverterEquipName            }
            STATUS current
            DESCRIPTION
                "AC Output Undervoltage.
                Its correlation binding parameters: 
                Site alarm serial number (SN),
                Alarm name,
                Alarm level,
                Site name,
                Site administrant address,
                NE ID,
                Site description,
                Additionally, in order to identify the device, rectifier equipment ID and equipment name are also include in VB(variable bondings)."
            ::= { hwInverterTrapPrefix 5 }

        hwInverterACOutLowAlarmResumeTrap NOTIFICATION-TYPE
            OBJECTS { hwAlarmTrapOrdinalNumber,hwAlarmText,hwAlarmLevel,hwAlarmSigDesc,hwSiteName,hwSiteAdminAddr,hwNetIdentifier,hwSiteDescription,hwInverterEquipId,hwInverterEquipName            }
            STATUS current
            DESCRIPTION
                "AC Output Undervoltage Resume.
                Its correlation binding parameters: 
                Site alarm serial number (SN),
                Alarm name,
                Alarm level,
                Site name,
                Site administrant address,
                NE ID,
                Site description,
                Additionally, in order to identify the device, rectifier equipment ID and equipment name are also include in VB(variable bondings)."
            ::= { hwInverterTrapPrefix 6 }

        hwInverterACOutHighAlarmTrap NOTIFICATION-TYPE
            OBJECTS { hwAlarmTrapOrdinalNumber,hwAlarmText,hwAlarmLevel,hwAlarmSigDesc,hwSiteName,hwSiteAdminAddr,hwNetIdentifier,hwSiteDescription,hwInverterEquipId,hwInverterEquipName            }
            STATUS current
            DESCRIPTION
                "AC Output Overvoltage.
                Its correlation binding parameters: 
                Site alarm serial number (SN),
                Alarm name,
                Alarm level,
                Site name,
                Site administrant address,
                NE ID,
                Site description,
                Additionally, in order to identify the device, rectifier equipment ID and equipment name are also include in VB(variable bondings)."
            ::= { hwInverterTrapPrefix 7 }

        hwInverterACOutHighAlarmResumeTrap NOTIFICATION-TYPE
            OBJECTS { hwAlarmTrapOrdinalNumber,hwAlarmText,hwAlarmLevel,hwAlarmSigDesc,hwSiteName,hwSiteAdminAddr,hwNetIdentifier,hwSiteDescription,hwInverterEquipId,hwInverterEquipName            }
            STATUS current
            DESCRIPTION
                "AC Output Overvoltage Resume.
                Its correlation binding parameters: 
                Site alarm serial number (SN),
                Alarm name,
                Alarm level,
                Site name,
                Site administrant address,
                NE ID,
                Site description,
                Additionally, in order to identify the device, rectifier equipment ID and equipment name are also include in VB(variable bondings)."
            ::= { hwInverterTrapPrefix 8 }

        hwInverterModFaultAlarmTrap NOTIFICATION-TYPE
            OBJECTS { hwAlarmTrapOrdinalNumber,hwAlarmText,hwAlarmLevel,hwAlarmSigDesc,hwSiteName,hwSiteAdminAddr,hwNetIdentifier,hwSiteDescription,hwInverterEquipId,hwInverterEquipName            }
            STATUS current
            DESCRIPTION
                "Module Fault.
                Its correlation binding parameters: 
                Site alarm serial number (SN),
                Alarm name,
                Alarm level,
                Site name,
                Site administrant address,
                NE ID,
                Site description,
                Additionally, in order to identify the device, rectifier equipment ID and equipment name are also include in VB(variable bondings)."
            ::= { hwInverterTrapPrefix 9 }

        hwInverterModFaultAlarmResumeTrap NOTIFICATION-TYPE
            OBJECTS { hwAlarmTrapOrdinalNumber,hwAlarmText,hwAlarmLevel,hwAlarmSigDesc,hwSiteName,hwSiteAdminAddr,hwNetIdentifier,hwSiteDescription,hwInverterEquipId,hwInverterEquipName            }
            STATUS current
            DESCRIPTION
                "Module Fault Resume.
                Its correlation binding parameters: 
                Site alarm serial number (SN),
                Alarm name,
                Alarm level,
                Site name,
                Site administrant address,
                NE ID,
                Site description,
                Additionally, in order to identify the device, rectifier equipment ID and equipment name are also include in VB(variable bondings)."
            ::= { hwInverterTrapPrefix 10 }

        hwInverterModTempHighAlarmTrap NOTIFICATION-TYPE
            OBJECTS { hwAlarmTrapOrdinalNumber,hwAlarmText,hwAlarmLevel,hwAlarmSigDesc,hwSiteName,hwSiteAdminAddr,hwNetIdentifier,hwSiteDescription,hwInverterEquipId,hwInverterEquipName            }
            STATUS current
            DESCRIPTION
                "Temperature Too High.
                Its correlation binding parameters: 
                Site alarm serial number (SN),
                Alarm name,
                Alarm level,
                Site name,
                Site administrant address,
                NE ID,
                Site description,
                Additionally, in order to identify the device, rectifier equipment ID and equipment name are also include in VB(variable bondings)."
            ::= { hwInverterTrapPrefix 11 }

        hwInverterModTempHighAlarmResumeTrap NOTIFICATION-TYPE
            OBJECTS { hwAlarmTrapOrdinalNumber,hwAlarmText,hwAlarmLevel,hwAlarmSigDesc,hwSiteName,hwSiteAdminAddr,hwNetIdentifier,hwSiteDescription,hwInverterEquipId,hwInverterEquipName            }
            STATUS current
            DESCRIPTION
                "Temperature Too High Resume.
                Its correlation binding parameters: 
                Site alarm serial number (SN),
                Alarm name,
                Alarm level,
                Site name,
                Site administrant address,
                NE ID,
                Site description,
                Additionally, in order to identify the device, rectifier equipment ID and equipment name are also include in VB(variable bondings)."
            ::= { hwInverterTrapPrefix 12 }

        hwInverterModTempLowAlarmTrap NOTIFICATION-TYPE
            OBJECTS { hwAlarmTrapOrdinalNumber,hwAlarmText,hwAlarmLevel,hwAlarmSigDesc,hwSiteName,hwSiteAdminAddr,hwNetIdentifier,hwSiteDescription,hwInverterEquipId,hwInverterEquipName            }
            STATUS current
            DESCRIPTION
                "Temperature Too Low.
                Its correlation binding parameters: 
                Site alarm serial number (SN),
                Alarm name,
                Alarm level,
                Site name,
                Site administrant address,
                NE ID,
                Site description,
                Additionally, in order to identify the device, rectifier equipment ID and equipment name are also include in VB(variable bondings)."
            ::= { hwInverterTrapPrefix 13 }

        hwInverterModTempLowAlarmResumeTrap NOTIFICATION-TYPE
            OBJECTS { hwAlarmTrapOrdinalNumber,hwAlarmText,hwAlarmLevel,hwAlarmSigDesc,hwSiteName,hwSiteAdminAddr,hwNetIdentifier,hwSiteDescription,hwInverterEquipId,hwInverterEquipName            }
            STATUS current
            DESCRIPTION
                "Temperature Too Low Resume.
                Its correlation binding parameters: 
                Site alarm serial number (SN),
                Alarm name,
                Alarm level,
                Site name,
                Site administrant address,
                NE ID,
                Site description,
                Additionally, in order to identify the device, rectifier equipment ID and equipment name are also include in VB(variable bondings)."
            ::= { hwInverterTrapPrefix 14 }

        hwInvertersACPhaseShortAlarmTrap NOTIFICATION-TYPE
            OBJECTS { hwAlarmTrapOrdinalNumber,hwAlarmText,hwAlarmLevel,hwAlarmSigDesc,hwSiteName,hwSiteAdminAddr,hwNetIdentifier,hwSiteDescription,hwInverterEquipId,hwInverterEquipName            }
            STATUS current
            DESCRIPTION
                "AC Input Phase Not Ready.
                Its correlation binding parameters: 
                Site alarm serial number (SN),
                Alarm name,
                Alarm level,
                Site name,
                Site administrant address,
                NE ID,
                Site description,
                Additionally, in order to identify the device, rectifier equipment ID and equipment name are also include in VB(variable bondings)."
            ::= { hwInverterTrapPrefix 15 }

        hwInvertersACPhaseShortAlarmResumeTrap NOTIFICATION-TYPE
            OBJECTS { hwAlarmTrapOrdinalNumber,hwAlarmText,hwAlarmLevel,hwAlarmSigDesc,hwSiteName,hwSiteAdminAddr,hwNetIdentifier,hwSiteDescription,hwInverterEquipId,hwInverterEquipName            }
            STATUS current
            DESCRIPTION
                "AC Input Phase Not Ready Resume.
                Its correlation binding parameters: 
                Site alarm serial number (SN),
                Alarm name,
                Alarm level,
                Site name,
                Site administrant address,
                NE ID,
                Site description,
                Additionally, in order to identify the device, rectifier equipment ID and equipment name are also include in VB(variable bondings)."
            ::= { hwInverterTrapPrefix 16 }

        hwInverterModOffAlarmTrap NOTIFICATION-TYPE
            OBJECTS { hwAlarmTrapOrdinalNumber,hwAlarmText,hwAlarmLevel,hwAlarmSigDesc,hwSiteName,hwSiteAdminAddr,hwNetIdentifier,hwSiteDescription,hwInverterEquipId,hwInverterEquipName            }
            STATUS current
            DESCRIPTION
                "Module Off.
                Its correlation binding parameters: 
                Site alarm serial number (SN),
                Alarm name,
                Alarm level,
                Site name,
                Site administrant address,
                NE ID,
                Site description,
                Additionally, in order to identify the device, rectifier equipment ID and equipment name are also include in VB(variable bondings)."
            ::= { hwInverterTrapPrefix 17 }

        hwInverterModOffAlarmResumeTrap NOTIFICATION-TYPE
            OBJECTS { hwAlarmTrapOrdinalNumber,hwAlarmText,hwAlarmLevel,hwAlarmSigDesc,hwSiteName,hwSiteAdminAddr,hwNetIdentifier,hwSiteDescription,hwInverterEquipId,hwInverterEquipName            }
            STATUS current
            DESCRIPTION
                "Module Off Resume.
                Its correlation binding parameters: 
                Site alarm serial number (SN),
                Alarm name,
                Alarm level,
                Site name,
                Site administrant address,
                NE ID,
                Site description,
                Additionally, in order to identify the device, rectifier equipment ID and equipment name are also include in VB(variable bondings)."
            ::= { hwInverterTrapPrefix 18 }

        hwInverterACInAbnAlarmTrap NOTIFICATION-TYPE
            OBJECTS { hwAlarmTrapOrdinalNumber,hwAlarmText,hwAlarmLevel,hwAlarmSigDesc,hwSiteName,hwSiteAdminAddr,hwNetIdentifier,hwSiteDescription,hwInverterEquipId,hwInverterEquipName            }
            STATUS current
            DESCRIPTION
                "AC Input Abnormal.
                Its correlation binding parameters: 
                Site alarm serial number (SN),
                Alarm name,
                Alarm level,
                Site name,
                Site administrant address,
                NE ID,
                Site description,
                Additionally, in order to identify the device, rectifier equipment ID and equipment name are also include in VB(variable bondings)."
            ::= { hwInverterTrapPrefix 19 }

        hwInverterACInAbnAlarmResumeTrap NOTIFICATION-TYPE
            OBJECTS { hwAlarmTrapOrdinalNumber,hwAlarmText,hwAlarmLevel,hwAlarmSigDesc,hwSiteName,hwSiteAdminAddr,hwNetIdentifier,hwSiteDescription,hwInverterEquipId,hwInverterEquipName            }
            STATUS current
            DESCRIPTION
                "AC Input Abnormal Resume.
                Its correlation binding parameters: 
                Site alarm serial number (SN),
                Alarm name,
                Alarm level,
                Site name,
                Site administrant address,
                NE ID,
                Site description,
                Additionally, in order to identify the device, rectifier equipment ID and equipment name are also include in VB(variable bondings)."
            ::= { hwInverterTrapPrefix 20 }

        hwInverterDCInLowAlarmTrap NOTIFICATION-TYPE
            OBJECTS { hwAlarmTrapOrdinalNumber,hwAlarmText,hwAlarmLevel,hwAlarmSigDesc,hwSiteName,hwSiteAdminAddr,hwNetIdentifier,hwSiteDescription,hwInverterEquipId,hwInverterEquipName            }
            STATUS current
            DESCRIPTION
                "DC Input Undervoltage.
                Its correlation binding parameters: 
                Site alarm serial number (SN),
                Alarm name,
                Alarm level,
                Site name,
                Site administrant address,
                NE ID,
                Site description,
                Additionally, in order to identify the device, rectifier equipment ID and equipment name are also include in VB(variable bondings)."
            ::= { hwInverterTrapPrefix 21 }

        hwInverteDCInLowAlarmResumeTrap NOTIFICATION-TYPE
            OBJECTS { hwAlarmTrapOrdinalNumber,hwAlarmText,hwAlarmLevel,hwAlarmSigDesc,hwSiteName,hwSiteAdminAddr,hwNetIdentifier,hwSiteDescription,hwInverterEquipId,hwInverterEquipName            }
            STATUS current
            DESCRIPTION
                "DC Input Undervoltage Resume.
                Its correlation binding parameters: 
                Site alarm serial number (SN),
                Alarm name,
                Alarm level,
                Site name,
                Site administrant address,
                NE ID,
                Site description,
                Additionally, in order to identify the device, rectifier equipment ID and equipment name are also include in VB(variable bondings)."
            ::= { hwInverterTrapPrefix 22 }

        hwInverterDCInHighAlarmTrap NOTIFICATION-TYPE
            OBJECTS { hwAlarmTrapOrdinalNumber,hwAlarmText,hwAlarmLevel,hwAlarmSigDesc,hwSiteName,hwSiteAdminAddr,hwNetIdentifier,hwSiteDescription,hwInverterEquipId,hwInverterEquipName            }
            STATUS current
            DESCRIPTION
                "DC Input Overvoltage.
                Its correlation binding parameters: 
                Site alarm serial number (SN),
                Alarm name,
                Alarm level,
                Site name,
                Site administrant address,
                NE ID,
                Site description,
                Additionally, in order to identify the device, rectifier equipment ID and equipment name are also include in VB(variable bondings)."
            ::= { hwInverterTrapPrefix 23 }

        hwInverterDCInHighAlarmResumeTrap NOTIFICATION-TYPE
            OBJECTS { hwAlarmTrapOrdinalNumber,hwAlarmText,hwAlarmLevel,hwAlarmSigDesc,hwSiteName,hwSiteAdminAddr,hwNetIdentifier,hwSiteDescription,hwInverterEquipId,hwInverterEquipName            }
            STATUS current
            DESCRIPTION
                "DC Input Overvoltage Resume.
                Its correlation binding parameters: 
                Site alarm serial number (SN),
                Alarm name,
                Alarm level,
                Site name,
                Site administrant address,
                NE ID,
                Site description,
                Additionally, in order to identify the device, rectifier equipment ID and equipment name are also include in VB(variable bondings)."
            ::= { hwInverterTrapPrefix 24 }

        hwInverterModCommFailAlarmTrap NOTIFICATION-TYPE
            OBJECTS { hwAlarmTrapOrdinalNumber,hwAlarmText,hwAlarmLevel,hwAlarmSigDesc,hwSiteName,hwSiteAdminAddr,hwNetIdentifier,hwSiteDescription,hwInverterEquipId,hwInverterEquipName            }
            STATUS current
            DESCRIPTION
                "Module Communication Failure.
                Its correlation binding parameters: 
                Site alarm serial number (SN),
                Alarm name,
                Alarm level,
                Site name,
                Site administrant address,
                NE ID,
                Site description,
                Additionally, in order to identify the device, rectifier equipment ID and equipment name are also include in VB(variable bondings)."
            ::= { hwInverterTrapPrefix 25 }

        hwInverterModCommFailAlarmResumeTrap NOTIFICATION-TYPE
            OBJECTS { hwAlarmTrapOrdinalNumber,hwAlarmText,hwAlarmLevel,hwAlarmSigDesc,hwSiteName,hwSiteAdminAddr,hwNetIdentifier,hwSiteDescription,hwInverterEquipId,hwInverterEquipName            }
            STATUS current
            DESCRIPTION
                "Module Communication Failure Resume.
                Its correlation binding parameters: 
                Site alarm serial number (SN),
                Alarm name,
                Alarm level,
                Site name,
                Site administrant address,
                NE ID,
                Site description,
                Additionally, in order to identify the device, rectifier equipment ID and equipment name are also include in VB(variable bondings)."
            ::= { hwInverterTrapPrefix 26 }

        hwInverterNoACInAlarmTrap NOTIFICATION-TYPE
            OBJECTS { hwAlarmTrapOrdinalNumber,hwAlarmText,hwAlarmLevel,hwAlarmSigDesc,hwSiteName,hwSiteAdminAddr,hwNetIdentifier,hwSiteDescription,hwInverterEquipId,hwInverterEquipName            }
            STATUS current
            DESCRIPTION
                "No AC In.
                Its correlation binding parameters: 
                Site alarm serial number (SN),
                Alarm name,
                Alarm level,
                Site name,
                Site administrant address,
                NE ID,
                Site description,
                Additionally, in order to identify the device, rectifier equipment ID and equipment name are also include in VB(variable bondings)."
            ::= { hwInverterTrapPrefix 27 }

        hwInverterNoACInAlarmResumeTrap NOTIFICATION-TYPE
            OBJECTS { hwAlarmTrapOrdinalNumber,hwAlarmText,hwAlarmLevel,hwAlarmSigDesc,hwSiteName,hwSiteAdminAddr,hwNetIdentifier,hwSiteDescription,hwInverterEquipId,hwInverterEquipName            }
            STATUS current
            DESCRIPTION
                "No AC In Resume.
                Its correlation binding parameters: 
                Site alarm serial number (SN),
                Alarm name,
                Alarm level,
                Site name,
                Site administrant address,
                NE ID,
                Site description,
                Additionally, in order to identify the device, rectifier equipment ID and equipment name are also include in VB(variable bondings)."
            ::= { hwInverterTrapPrefix 28 }

        hwInverterNoDCInAlarmTrap NOTIFICATION-TYPE
            OBJECTS { hwAlarmTrapOrdinalNumber,hwAlarmText,hwAlarmLevel,hwAlarmSigDesc,hwSiteName,hwSiteAdminAddr,hwNetIdentifier,hwSiteDescription,hwInverterEquipId,hwInverterEquipName            }
            STATUS current
            DESCRIPTION
                "No DC In.
                Its correlation binding parameters: 
                Site alarm serial number (SN),
                Alarm name,
                Alarm level,
                Site name,
                Site administrant address,
                NE ID,
                Site description,
                Additionally, in order to identify the device, rectifier equipment ID and equipment name are also include in VB(variable bondings)."
            ::= { hwInverterTrapPrefix 29 }

        hwInverterNoDCInAlarmResumeTrap NOTIFICATION-TYPE
            OBJECTS { hwAlarmTrapOrdinalNumber,hwAlarmText,hwAlarmLevel,hwAlarmSigDesc,hwSiteName,hwSiteAdminAddr,hwNetIdentifier,hwSiteDescription,hwInverterEquipId,hwInverterEquipName            }
            STATUS current
            DESCRIPTION
                "No DC In Resume.
                Its correlation binding parameters: 
                Site alarm serial number (SN),
                Alarm name,
                Alarm level,
                Site name,
                Site administrant address,
                NE ID,
                Site description,
                Additionally, in order to identify the device, rectifier equipment ID and equipment name are also include in VB(variable bondings)."
            ::= { hwInverterTrapPrefix 30 }

        hwInverterT2SFaultAlarmTrap NOTIFICATION-TYPE
            OBJECTS { hwAlarmTrapOrdinalNumber,hwAlarmText,hwAlarmLevel,hwAlarmSigDesc,hwSiteName,hwSiteAdminAddr,hwNetIdentifier,hwSiteDescription,hwInverterEquipId,hwInverterEquipName            }
            STATUS current
            DESCRIPTION
                "T2S Fault.
                Its correlation binding parameters: 
                Site alarm serial number (SN),
                Alarm name,
                Alarm level,
                Site name,
                Site administrant address,
                NE ID,
                Site description,
                Additionally, in order to identify the device, rectifier equipment ID and equipment name are also include in VB(variable bondings)."
            ::= { hwInverterTrapPrefix 31 }

        hwInverterT2SFaultAlarmResumeTrap NOTIFICATION-TYPE
            OBJECTS { hwAlarmTrapOrdinalNumber,hwAlarmText,hwAlarmLevel,hwAlarmSigDesc,hwSiteName,hwSiteAdminAddr,hwNetIdentifier,hwSiteDescription,hwInverterEquipId,hwInverterEquipName            }
            STATUS current
            DESCRIPTION
                "T2S Fault Resume.
                Its correlation binding parameters: 
                Site alarm serial number (SN),
                Alarm name,
                Alarm level,
                Site name,
                Site administrant address,
                NE ID,
                Site description,
                Additionally, in order to identify the device, rectifier equipment ID and equipment name are also include in VB(variable bondings)."
            ::= { hwInverterTrapPrefix 32 }

        hwInvertModMissAlarmTrap NOTIFICATION-TYPE
            OBJECTS { hwAlarmTrapOrdinalNumber,hwAlarmText,hwAlarmLevel,hwAlarmSigDesc,hwSiteName,hwSiteAdminAddr,hwNetIdentifier,hwSiteDescription,hwInverterEquipId,hwInverterEquipName            }
            STATUS current
            DESCRIPTION
                "Missing Module.
                Its correlation binding parameters: 
                Site alarm serial number (SN),
                Alarm name,
                Alarm level,
                Site name,
                Site administrant address,
                NE ID,
                Site description,
                Additionally, in order to identify the device, rectifier equipment ID and equipment name are also include in VB(variable bondings)."
            ::= { hwInverterTrapPrefix 33 }

        hwInvertModMissAlarmResumeTrap NOTIFICATION-TYPE
            OBJECTS { hwAlarmTrapOrdinalNumber,hwAlarmText,hwAlarmLevel,hwAlarmSigDesc,hwSiteName,hwSiteAdminAddr,hwNetIdentifier,hwSiteDescription,hwInverterEquipId,hwInverterEquipName            }
            STATUS current
            DESCRIPTION
                "Missing Module Resume.
                Its correlation binding parameters: 
                Site alarm serial number (SN),
                Alarm name,
                Alarm level,
                Site name,
                Site administrant address,
                NE ID,
                Site description,
                Additionally, in order to identify the device, rectifier equipment ID and equipment name are also include in VB(variable bondings)."
            ::= { hwInverterTrapPrefix 34 }

        hwIboxAlmTrapTable OBJECT IDENTIFIER ::= { hwSiteAlarmTraps 6 }

        hwIboxAlmTrapPrefix OBJECT IDENTIFIER ::= { hwIboxAlmTrapTable 0 }

        hwIboxCommFailAlarmTrap NOTIFICATION-TYPE
            OBJECTS { hwAlarmTrapOrdinalNumber,hwAlarmText,hwAlarmLevel,hwAlarmSigDesc,hwSiteName,hwSiteAdminAddr,hwNetIdentifier,hwSiteDescription,hwIboxEquipId,hwIboxEquipName            }
            STATUS current
            DESCRIPTION
                "Ibox Communication Failure.
                Its correlation binding parameters: 
                Site alarm serial number (SN),
                Alarm name,
                Alarm level,
                Site name,
                Site administrant address,
                NE ID,
                Site description,
                Additionally, in order to identify the device, rectifier equipment ID and equipment name are also include in VB(variable bondings)."
            ::= { hwIboxAlmTrapPrefix 1 }

        hwIboxCommFailAlarmResumeTrap NOTIFICATION-TYPE
            OBJECTS { hwAlarmTrapOrdinalNumber,hwAlarmText,hwAlarmLevel,hwAlarmSigDesc,hwSiteName,hwSiteAdminAddr,hwNetIdentifier,hwSiteDescription,hwIboxEquipId,hwIboxEquipName            }
            STATUS current
            DESCRIPTION
                "Ibox Communication Failure Resume.
                Its correlation binding parameters: 
                Site alarm serial number (SN),
                Alarm name,
                Alarm level,
                Site name,
                Site administrant address,
                NE ID,
                Site description,
                Additionally, in order to identify the device, rectifier equipment ID and equipment name are also include in VB(variable bondings)."
            ::= { hwIboxAlmTrapPrefix 2 }

        hwIbatAlmTrapTable OBJECT IDENTIFIER ::= { hwSiteAlarmTraps 7 }

        hwIbatAlmTrapPrefix OBJECT IDENTIFIER ::= { hwIbatAlmTrapTable 0 }

        hwIbatAlarmTrap NOTIFICATION-TYPE
            OBJECTS { hwAlarmTrapOrdinalNumber,hwAlarmText,hwAlarmLevel,hwAlarmSigDesc,hwSiteName,hwSiteAdminAddr,hwNetIdentifier,hwSiteDescription,hwIbatEquipId,hwIbatEquipName            }
            STATUS current
            DESCRIPTION
                "Ibat Communication Failure.
                Its correlation binding parameters: 
                Site alarm serial number (SN),
                Alarm name,
                Alarm level,
                Site name,
                Site administrant address,
                NE ID,
                Site description,
                Additionally, in order to identify the device, rectifier equipment ID and equipment name are also include in VB(variable bondings)."
            ::= { hwIbatAlmTrapPrefix 1 }

        hwIbatAlarmResumeTrap NOTIFICATION-TYPE
            OBJECTS { hwAlarmTrapOrdinalNumber,hwAlarmText,hwAlarmLevel,hwAlarmSigDesc,hwSiteName,hwSiteAdminAddr,hwNetIdentifier,hwSiteDescription,hwIbatEquipId,hwIbatEquipName            }
            STATUS current
            DESCRIPTION
                "Ibat Communication Failure Resume.
                Its correlation binding parameters: 
                Site alarm serial number (SN),
                Alarm name,
                Alarm level,
                Site name,
                Site administrant address,
                NE ID,
                Site description,
                Additionally, in order to identify the device, rectifier equipment ID and equipment name are also include in VB(variable bondings)."
            ::= { hwIbatAlmTrapPrefix 2 }

        hwAcAmmeterAlmTrapTable OBJECT IDENTIFIER ::= { hwSiteAlarmTraps 8 }

        hwAcAmmeterAlmTrapPrefix OBJECT IDENTIFIER ::= { hwAcAmmeterAlmTrapTable 0 }

        hwAcAmmeterAlarmTrap NOTIFICATION-TYPE
            OBJECTS { hwAlarmTrapOrdinalNumber,hwAlarmText,hwAlarmLevel,hwAlarmSigDesc,hwSiteName,hwSiteAdminAddr,hwNetIdentifier,hwSiteDescription,hwAcAmmeterEquipId,hwAcAmmeterEquipName            }
            STATUS current
            DESCRIPTION
                "Ac Ammeter.
                Its correlation binding parameters: 
                Site alarm serial number (SN),
                Alarm name,
                Alarm level,
                Site name,
                Site administrant address,
                NE ID,
                Site description,
                Additionally, in order to identify the device, rectifier equipment ID and equipment name are also include in VB(variable bondings)."
            ::= { hwAcAmmeterAlmTrapPrefix 1 }

        hwAcAmmeterAlarmResumeTrap NOTIFICATION-TYPE
            OBJECTS { hwAlarmTrapOrdinalNumber,hwAlarmText,hwAlarmLevel,hwAlarmSigDesc,hwSiteName,hwSiteAdminAddr,hwNetIdentifier,hwSiteDescription,hwAcAmmeterEquipId,hwAcAmmeterEquipName            }
            STATUS current
            DESCRIPTION
                "Ac Ammeter .
                Its correlation binding parameters: 
                Site alarm serial number (SN),
                Alarm name,
                Alarm level,
                Site name,
                Site administrant address,
                NE ID,
                Site description,
                Additionally, in order to identify the device, rectifier equipment ID and equipment name are also include in VB(variable bondings)."
            ::= { hwAcAmmeterAlmTrapPrefix 2 }

        hwCommExBoardAlmTrapTable OBJECT IDENTIFIER ::= { hwSiteAlarmTraps 9 }

        hwCommExBoardAlmTrapPrefix OBJECT IDENTIFIER ::= { hwCommExBoardAlmTrapTable 0 }

        hwCommExBoardCommFailAlarmTrap NOTIFICATION-TYPE
            OBJECTS { hwAlarmTrapOrdinalNumber,hwAlarmText,hwAlarmLevel,hwAlarmSigDesc,hwSiteName,hwSiteAdminAddr,hwNetIdentifier,hwSiteDescription,hwCommExBoardEquipId,hwCommExBoardEquipName            }
            STATUS current
            DESCRIPTION
                "Communication Expansion Board Communication Failure
                Its correlation binding parameters: 
                Site alarm serial number (SN),
                Alarm name,
                Alarm level,
                Site name,
                Site administrant address,
                NE ID,
                Site description,
                Additionally, in order to identify the device, rectifier equipment ID and equipment name are also include in VB(variable bondings)."
            ::= { hwCommExBoardAlmTrapPrefix 1 }

        hwCommExBoardCommFailAlarmResumeTrap NOTIFICATION-TYPE
            OBJECTS { hwAlarmTrapOrdinalNumber,hwAlarmText,hwAlarmLevel,hwAlarmSigDesc,hwSiteName,hwSiteAdminAddr,hwNetIdentifier,hwSiteDescription,hwCommExBoardEquipId,hwCommExBoardEquipName            }
            STATUS current
            DESCRIPTION
                "Communication Expansion Board Communication Failure Resume.
                Its correlation binding parameters: 
                Site alarm serial number (SN),
                Alarm name,
                Alarm level,
                Site name,
                Site administrant address,
                NE ID,
                Site description,
                Additionally, in order to identify the device, rectifier equipment ID and equipment name are also include in VB(variable bondings)."
            ::= { hwCommExBoardAlmTrapPrefix 2 }

        hwDGCommExBoardAlmTrapTable OBJECT IDENTIFIER ::= { hwSiteAlarmTraps 10 }

        hwDGCommExBoardAlmTrapPrefix OBJECT IDENTIFIER ::= { hwDGCommExBoardAlmTrapTable 0 }

        hwDGCommExBoardCommFailAlarmTrap NOTIFICATION-TYPE
            OBJECTS { hwAlarmTrapOrdinalNumber,hwAlarmText,hwAlarmLevel,hwAlarmSigDesc,hwSiteName,hwSiteAdminAddr,hwNetIdentifier,hwSiteDescription,hwDGCommExBoardEquipId,hwDGCommExBoardEquipName            }
            STATUS current
            DESCRIPTION
                "DG Comm Ex Board Communication Failure.
                Its correlation binding parameters: 
                Site alarm serial number (SN),
                Alarm name,
                Alarm level,
                Site name,
                Site administrant address,
                NE ID,
                Site description,
                Additionally, in order to identify the device, rectifier equipment ID and equipment name are also include in VB(variable bondings)."
            ::= { hwDGCommExBoardAlmTrapPrefix 1 }

        hwDGCommExBoardCommFailAlarmResumeTrap NOTIFICATION-TYPE
            OBJECTS { hwAlarmTrapOrdinalNumber,hwAlarmText,hwAlarmLevel,hwAlarmSigDesc,hwSiteName,hwSiteAdminAddr,hwNetIdentifier,hwSiteDescription,hwDGCommExBoardEquipId,hwDGCommExBoardEquipName            }
            STATUS current
            DESCRIPTION
                "DG Comm Ex Board Communication Failure Resume.
                Its correlation binding parameters: 
                Site alarm serial number (SN),
                Alarm name,
                Alarm level,
                Site name,
                Site administrant address,
                NE ID,
                Site description,
                Additionally, in order to identify the device, rectifier equipment ID and equipment name are also include in VB(variable bondings)."
            ::= { hwDGCommExBoardAlmTrapPrefix 2 }

        hwAcbGroupAlmTrapTable OBJECT IDENTIFIER ::= { hwSiteAlarmTraps 2 }

        hwAcbGroupAlmTrapTablePrefix OBJECT IDENTIFIER ::= { hwAcbGroupAlmTrapTable 0 }

        hwAcbGroupAlarmTrap NOTIFICATION-TYPE
            OBJECTS { hwAlarmTrapOrdinalNumber,hwAlarmText,hwAlarmLevel,hwAlarmSigDesc,hwSiteName,hwSiteAdminAddr,hwNetIdentifier,hwSiteDescription,hwAcbGroupEquipId,hwAcbGroupEquipName            }
            STATUS current
            DESCRIPTION
                "/"
            ::= { hwAcbGroupAlmTrapTablePrefix 99 }

        hwAcbGroupAarlmResumeTrap NOTIFICATION-TYPE
            OBJECTS { hwAlarmTrapOrdinalNumber,hwAlarmText,hwAlarmLevel,hwAlarmSigDesc,hwSiteName,hwSiteAdminAddr,hwNetIdentifier,hwSiteDescription,hwAcbGroupEquipId,hwAcbGroupEquipName            }
            STATUS current
            DESCRIPTION
                "/"
            ::= { hwAcbGroupAlmTrapTablePrefix 100 }

        hwAcbAlmTrapTable OBJECT IDENTIFIER ::= { hwSiteAlarmTraps 3 }

        hwAcbAlmTrapTablePrefix OBJECT IDENTIFIER ::= { hwAcbAlmTrapTable 0 }

        hwAcbAlarmTrap NOTIFICATION-TYPE
            OBJECTS { hwAlarmTrapOrdinalNumber,hwAlarmText,hwAlarmLevel,hwAlarmSigDesc,hwSiteName,hwSiteAdminAddr,hwNetIdentifier,hwSiteDescription,hwAcbEquipId,hwAcbEquipName,hwAcbFatherEquipname            }
            STATUS current
            DESCRIPTION
                "/"
            ::= { hwAcbAlmTrapTablePrefix 99 }

        hwAcbAarlmResumeTrap NOTIFICATION-TYPE
            OBJECTS { hwAlarmTrapOrdinalNumber,hwAlarmText,hwAlarmLevel,hwAlarmSigDesc,hwSiteName,hwSiteAdminAddr,hwNetIdentifier,hwSiteDescription,hwAcbEquipId,hwAcbEquipName,hwAcbFatherEquipname            }
            STATUS current
            DESCRIPTION
                "/"
            ::= { hwAcbAlmTrapTablePrefix 100 }

        hwElockAlmTrapTable OBJECT IDENTIFIER ::= { hwSiteAlarmTraps 13 }

        hwElockAlmTrapTablePrefix OBJECT IDENTIFIER ::= { hwElockAlmTrapTable 0 }

        hwElockAlarmTrap NOTIFICATION-TYPE
            OBJECTS { hwAlarmTrapOrdinalNumber,hwAlarmText,hwAlarmLevel,hwAlarmSigDesc,hwSiteName,hwSiteAdminAddr,hwNetIdentifier,hwSiteDescription,hwElockEquipId,hwElockEquipName            }
            STATUS current
            DESCRIPTION
                "/"
            ::= { hwElockAlmTrapTablePrefix 1 }

        hwElockAlarmResumeTrap NOTIFICATION-TYPE
            OBJECTS { hwAlarmTrapOrdinalNumber,hwAlarmText,hwAlarmLevel,hwAlarmSigDesc,hwSiteName,hwSiteAdminAddr,hwNetIdentifier,hwSiteDescription,hwElockEquipId,hwElockEquipName            }
            STATUS current
            DESCRIPTION
                "/"
            ::= { hwElockAlmTrapTablePrefix 2 }

        hwTemHumAlmTrapTable OBJECT IDENTIFIER ::= { hwSiteAlarmTraps 14 }

        hwTemHumAlmTrapTablePrefix OBJECT IDENTIFIER ::= { hwTemHumAlmTrapTable 0 }

        hwTemHumAlarmTrap NOTIFICATION-TYPE
            OBJECTS { hwAlarmTrapOrdinalNumber,hwAlarmText,hwAlarmLevel,hwAlarmSigDesc,hwSiteName,hwSiteAdminAddr,hwNetIdentifier,hwSiteDescription,hwTemHumEquipId,hwTemHumEquipName            }
            STATUS current
            DESCRIPTION
                "/"
            ::= { hwTemHumAlmTrapTablePrefix 1 }

        hwTemHumAlarmResumeTrap NOTIFICATION-TYPE
            OBJECTS { hwAlarmTrapOrdinalNumber,hwAlarmText,hwAlarmLevel,hwAlarmSigDesc,hwSiteName,hwSiteAdminAddr,hwNetIdentifier,hwSiteDescription,hwTemHumEquipId,hwTemHumEquipName            }
            STATUS current
            DESCRIPTION
                "/"
            ::= { hwTemHumAlmTrapTablePrefix 2 }

        hwLiBatteryCabinetAlmTrapTable OBJECT IDENTIFIER ::= { hwSiteAlarmTraps 15 }

        hwLiBatteryCabinetAlmTrapTablePrefix OBJECT IDENTIFIER ::= { hwLiBatteryCabinetAlmTrapTable 0 }

        hwLiBatteryCabinetAlarmTrap NOTIFICATION-TYPE
            OBJECTS { hwAlarmTrapOrdinalNumber,hwAlarmText,hwAlarmLevel,hwAlarmSigDesc,hwSiteName,hwSiteAdminAddr,hwNetIdentifier,hwSiteDescription,hwLiBatteryCabinetEquipId,hwLiBatteryCabinetEquipName            }
            STATUS current
            DESCRIPTION
                "/"
            ::= { hwLiBatteryCabinetAlmTrapTablePrefix 1 }

        hwLiBatteryCabinetAlarmResumeTrap NOTIFICATION-TYPE
            OBJECTS { hwAlarmTrapOrdinalNumber,hwAlarmText,hwAlarmLevel,hwAlarmSigDesc,hwSiteName,hwSiteAdminAddr,hwNetIdentifier,hwSiteDescription,hwLiBatteryCabinetEquipId,hwLiBatteryCabinetEquipName            }
            STATUS current
            DESCRIPTION
                "/"
            ::= { hwLiBatteryCabinetAlmTrapTablePrefix 2 }

        hwDcCabinetAlmTrapTable OBJECT IDENTIFIER ::= { hwSiteAlarmTraps 16 }

        hwDcCabinetAlmTrapTablePrefix OBJECT IDENTIFIER ::= { hwDcCabinetAlmTrapTable 0 }

        hwDcCabinetAlarmTrap NOTIFICATION-TYPE
            OBJECTS { hwAlarmTrapOrdinalNumber,hwAlarmText,hwAlarmLevel,hwAlarmSigDesc,hwSiteName,hwSiteAdminAddr,hwNetIdentifier,hwSiteDescription,hwDcCabinetEquipId,hwDcCabinetEquipName            }
            STATUS current
            DESCRIPTION
                "/"
            ::= { hwDcCabinetAlmTrapTablePrefix 1 }

        hwDcCabinetAarlmResumeTrap NOTIFICATION-TYPE
            OBJECTS { hwAlarmTrapOrdinalNumber,hwAlarmText,hwAlarmLevel,hwAlarmSigDesc,hwSiteName,hwSiteAdminAddr,hwNetIdentifier,hwSiteDescription,hwDcCabinetEquipId,hwDcCabinetEquipName            }
            STATUS current
            DESCRIPTION
                "/"
            ::= { hwDcCabinetAlmTrapTablePrefix 2 }

        hwCombinedCabinetAlmTrapTable OBJECT IDENTIFIER ::= { hwSiteAlarmTraps 17 }

        hwCombinedCabinetAlmTrapTablePrefix OBJECT IDENTIFIER ::= { hwCombinedCabinetAlmTrapTable 0 }

        hwCombinedCabinetAlarmTrap NOTIFICATION-TYPE
            OBJECTS { hwAlarmTrapOrdinalNumber,hwAlarmText,hwAlarmLevel,hwAlarmSigDesc,hwSiteName,hwSiteAdminAddr,hwNetIdentifier,hwSiteDescription,hwCombinedCabinetEquipId,hwCombinedCabinetEquipName            }
            STATUS current
            DESCRIPTION
                "/"
            ::= { hwCombinedCabinetAlmTrapTablePrefix 1 }

        hwCombinedCabinetAarlmResumeTrap NOTIFICATION-TYPE
            OBJECTS { hwAlarmTrapOrdinalNumber,hwAlarmText,hwAlarmLevel,hwAlarmSigDesc,hwSiteName,hwSiteAdminAddr,hwNetIdentifier,hwSiteDescription,hwCombinedCabinetEquipId,hwCombinedCabinetEquipName            }
            STATUS current
            DESCRIPTION
                "/"
            ::= { hwCombinedCabinetAlmTrapTablePrefix 2 }

        hwRectifierCabinetAlmTrapTable OBJECT IDENTIFIER ::= { hwSiteAlarmTraps 18 }

        hwRectifierCabinetAlmTrapPrefix OBJECT IDENTIFIER ::= { hwRectifierCabinetAlmTrapTable 0 }

        hwRectifierCabinetAlarmTrap NOTIFICATION-TYPE
            OBJECTS { hwAlarmTrapOrdinalNumber,hwAlarmText,hwAlarmLevel,hwAlarmSigDesc,hwSiteName,hwSiteAdminAddr,hwNetIdentifier,hwSiteDescription,hwRectifierCabinetEquipId,hwRectifierCabinetEquipName            }
            STATUS current
            DESCRIPTION
                "/"
            ::= { hwRectifierCabinetAlmTrapPrefix 1 }

        hwRectifierCabinetAarlmResumeTrap NOTIFICATION-TYPE
            OBJECTS { hwAlarmTrapOrdinalNumber,hwAlarmText,hwAlarmLevel,hwAlarmSigDesc,hwSiteName,hwSiteAdminAddr,hwNetIdentifier,hwSiteDescription,hwRectifierCabinetEquipId,hwRectifierCabinetEquipName            }
            STATUS current
            DESCRIPTION
                "/"
            ::= { hwRectifierCabinetAlmTrapPrefix 2 }

        hwAcCabinetAlmTrapTable OBJECT IDENTIFIER ::= { hwSiteAlarmTraps 19 }

        hwAcCabinetAlmTrapPrefix OBJECT IDENTIFIER ::= { hwAcCabinetAlmTrapTable 0 }

        hwAcCabinetAlarmTrap NOTIFICATION-TYPE
            OBJECTS { hwAlarmTrapOrdinalNumber,hwAlarmText,hwAlarmLevel,hwAlarmSigDesc,hwSiteName,hwSiteAdminAddr,hwNetIdentifier,hwSiteDescription,hwAcCabinetEquipId,hwAcCabinetEquipName            }
            STATUS current
            DESCRIPTION
                "/"
            ::= { hwAcCabinetAlmTrapPrefix 1 }

        hwAcCabinetAarlmResumeTrap NOTIFICATION-TYPE
            OBJECTS { hwAlarmTrapOrdinalNumber,hwAlarmText,hwAlarmLevel,hwAlarmSigDesc,hwSiteName,hwSiteAdminAddr,hwNetIdentifier,hwSiteDescription,hwAcCabinetEquipId,hwAcCabinetEquipName            }
            STATUS current
            DESCRIPTION
                "/"
            ::= { hwAcCabinetAlmTrapPrefix 2 }

        hwLocalDCPowerAlmTrapTable OBJECT IDENTIFIER ::= { hwSiteAlarmTraps 20 }

        hwLocalDCPowerAlmTrapPrefix OBJECT IDENTIFIER ::= { hwLocalDCPowerAlmTrapTable 0 }

        hwLocalDCPowerAlarmTrap NOTIFICATION-TYPE
            OBJECTS { hwAlarmTrapOrdinalNumber,hwAlarmText,hwAlarmLevel,hwAlarmSigDesc,hwSiteName,hwSiteAdminAddr,hwNetIdentifier,hwSiteDescription,hwLocalDCPowerEquipId,hwLocalDCPowerEquipName            }
            STATUS current
            DESCRIPTION
                "The alarm of DC power device lost."
            ::= { hwLocalDCPowerAlmTrapPrefix 1 }

        hwLocalDCPowerAlarmResumeTrap NOTIFICATION-TYPE
            OBJECTS { hwAlarmTrapOrdinalNumber,hwAlarmText,hwAlarmLevel,hwAlarmSigDesc,hwSiteName,hwSiteAdminAddr,hwNetIdentifier,hwSiteDescription,hwLocalDCPowerEquipId,hwLocalDCPowerEquipName            }
            STATUS current
            DESCRIPTION
                "The alarm of DC power device lost resume."
            ::= { hwLocalDCPowerAlmTrapPrefix 2 }

        hwACSamplingUnitAlmTrapTable OBJECT IDENTIFIER ::= { hwSiteAlarmTraps 21 }

        hwACSamplingUnitAlmTrapPrefix OBJECT IDENTIFIER ::= { hwACSamplingUnitAlmTrapTable 0 }

        hwACSamplingUnitAlarmTrap NOTIFICATION-TYPE
            OBJECTS { hwAlarmTrapOrdinalNumber,hwAlarmText,hwAlarmLevel,hwAlarmSigDesc,hwSiteName,hwSiteAdminAddr,hwNetIdentifier,hwSiteDescription,hwACSamplingUnitEquipId,hwACSamplingUnitEquipName            }
            STATUS current
            DESCRIPTION
                "/"
            ::= { hwACSamplingUnitAlmTrapPrefix 1 }

        hwACSamplingUnitAarlmResumeTrap NOTIFICATION-TYPE
            OBJECTS { hwAlarmTrapOrdinalNumber,hwAlarmText,hwAlarmLevel,hwAlarmSigDesc,hwSiteName,hwSiteAdminAddr,hwNetIdentifier,hwSiteDescription,hwACSamplingUnitEquipId,hwACSamplingUnitEquipName            }
            STATUS current
            DESCRIPTION
                "/"
            ::= { hwACSamplingUnitAlmTrapPrefix 2 }

        hwDCSamplingUnitAlmTrapTable OBJECT IDENTIFIER ::= { hwSiteAlarmTraps 22 }

        hwDCSamplingUnitAlmTrapPrefix OBJECT IDENTIFIER ::= { hwDCSamplingUnitAlmTrapTable 0 }

        hwDCSamplingUnitAlarmTrap NOTIFICATION-TYPE
            OBJECTS { hwAlarmTrapOrdinalNumber,hwAlarmText,hwAlarmLevel,hwAlarmSigDesc,hwSiteName,hwSiteAdminAddr,hwNetIdentifier,hwSiteDescription,hwDCSamplingUnitEquipId,hwDCSamplingUnitEquipName            }
            STATUS current
            DESCRIPTION
                "The alarm of DC samping unit."
            ::= { hwDCSamplingUnitAlmTrapPrefix 1 }

        hwDCSamplingUnitAarlmResumeTrap NOTIFICATION-TYPE
            OBJECTS { hwAlarmTrapOrdinalNumber,hwAlarmText,hwAlarmLevel,hwAlarmSigDesc,hwSiteName,hwSiteAdminAddr,hwNetIdentifier,hwSiteDescription,hwDCSamplingUnitEquipId,hwDCSamplingUnitEquipName            }
            STATUS current
            DESCRIPTION
                "The alarm of DC samping unit."
            ::= { hwDCSamplingUnitAlmTrapPrefix 2 }

        hwDCOutputDistributionAlmTrapTable OBJECT IDENTIFIER ::= { hwSiteAlarmTraps 23 }

        hwDCOutputDistributionAlmTrapPrefix OBJECT IDENTIFIER ::= { hwDCOutputDistributionAlmTrapTable 0 }

        hwDCOutputDistributionAlarmTrap NOTIFICATION-TYPE
            OBJECTS { hwAlarmTrapOrdinalNumber,hwAlarmText,hwAlarmLevel,hwAlarmSigDesc,hwSiteName,hwSiteAdminAddr,hwNetIdentifier,hwSiteDescription,hwDcOutputEquipId,hwDcOutputEquipName,hwDcFatherEquipname            }
            STATUS current
            DESCRIPTION
                "The alarm of DC samping unit no response."
            ::= { hwDCOutputDistributionAlmTrapPrefix 1 }

        hwDCOutputDistributionAarlmResumeTrap NOTIFICATION-TYPE
            OBJECTS { hwAlarmTrapOrdinalNumber,hwAlarmText,hwAlarmLevel,hwAlarmSigDesc,hwSiteName,hwSiteAdminAddr,hwNetIdentifier,hwSiteDescription,hwDcOutputEquipId,hwDcOutputEquipName,hwDcFatherEquipname            }
            STATUS current
            DESCRIPTION
                "The alarm of DC samping unit no response resume."
            ::= { hwDCOutputDistributionAlmTrapPrefix 2 }

        hwFuelTankAlmTrapTable OBJECT IDENTIFIER ::= { hwSiteAlarmTraps 29 }

        hwFuelTankAlmTrapPrefix OBJECT IDENTIFIER ::= { hwFuelTankAlmTrapTable 0 }

        hwFuelTankAlarmTrap NOTIFICATION-TYPE
            OBJECTS { hwAlarmTrapOrdinalNumber,hwAlarmText,hwAlarmLevel,hwAlarmSigDesc,hwSiteName,hwSiteAdminAddr,hwNetIdentifier,hwSiteDescription,hwFuelTankEquipId,hwFuelTankEquipName            }
            STATUS current
            DESCRIPTION
                "/"
            ::= { hwFuelTankAlmTrapPrefix 1 }

        hwFuelTankAlarmResumeTrap NOTIFICATION-TYPE
            OBJECTS { hwAlarmTrapOrdinalNumber,hwAlarmText,hwAlarmLevel,hwAlarmSigDesc,hwSiteName,hwSiteAdminAddr,hwNetIdentifier,hwSiteDescription,hwFuelTankEquipId,hwFuelTankEquipName            }
            STATUS current
            DESCRIPTION
                "/"
            ::= { hwFuelTankAlmTrapPrefix 2 }

        hwHWInverterShelfAlmTrapTable OBJECT IDENTIFIER ::= { hwSiteAlarmTraps 24 }

        hwHWInverterShelfAlmTrapPrefix  OBJECT IDENTIFIER ::= { hwHWInverterShelfAlmTrapTable 0 }

        hwHWInverterShelfAlarmTrap NOTIFICATION-TYPE
            OBJECTS { hwAlarmTrapOrdinalNumber,hwAlarmText,hwAlarmLevel,hwAlarmSigDesc,hwSiteName,hwSiteAdminAddr,hwNetIdentifier,hwSiteDescription,hwHWInverterShelfId,hwHWInverterShelfName,hwHWInverterShelfFatherEquipName            }
            STATUS current
            DESCRIPTION
                "HW Inverter Shelf equipment alarm. 
                Its correlation binding parameters: 
                Site alarm serial number (SN),
                Alarm name,
                Alarm level,
                Site name,
                Site administrant address,
                NE ID,
                Site description,
                Additionally, in order to identify the device, equipment ID and equipment name are also include in VB(variable bondings)."
            ::= { hwHWInverterShelfAlmTrapPrefix  1 }

        hwHWInverterShelfAlarmResumeTrap NOTIFICATION-TYPE
            OBJECTS { hwAlarmTrapOrdinalNumber,hwAlarmText,hwAlarmLevel,hwAlarmSigDesc,hwSiteName,hwSiteAdminAddr,hwNetIdentifier,hwSiteDescription,hwHWInverterShelfId,hwHWInverterShelfName,hwHWInverterShelfFatherEquipName            }
            STATUS current
            DESCRIPTION
                "HW Inverter Shelf equipment alarm resume.
                Its correlation binding parameters: 
                Site alarm serial number (SN),
                Alarm name,
                Alarm level,
                Site name,
                Site administrant address,
                NE ID,
                Site description,
                Additionally, in order to identify the device, equipment ID and equipment name are also include in VB(variable bondings)."
            ::= { hwHWInverterShelfAlmTrapPrefix  2 }

        hwHWInverterECMAlmTrapTable OBJECT IDENTIFIER ::= { hwSiteAlarmTraps 25 }

        hwHWInverterECMAlmTrapPrefix  OBJECT IDENTIFIER ::= { hwHWInverterECMAlmTrapTable 0 }

        hwHWInverterECMAlarmTrap NOTIFICATION-TYPE
            OBJECTS { hwAlarmTrapOrdinalNumber,hwAlarmText,hwAlarmLevel,hwAlarmSigDesc,hwSiteName,hwSiteAdminAddr,hwNetIdentifier,hwSiteDescription,hwECMEquipId,hwECMEquipName,hwECMFatherEquipName            }
            STATUS current
            DESCRIPTION
                "HW Inverter ECM equipment alarm. 
                Its correlation binding parameters: 
                Site alarm serial number (SN),
                Alarm name,
                Alarm level,
                Site name,
                Site administrant address,
                NE ID,
                Site description,
                Additionally, in order to identify the device, equipment ID and equipment name are also include in VB(variable bondings)."
            ::= { hwHWInverterECMAlmTrapPrefix  1 }

        hwHWInverterECMAlarmResumeTrap NOTIFICATION-TYPE
            OBJECTS { hwAlarmTrapOrdinalNumber,hwAlarmText,hwAlarmLevel,hwAlarmSigDesc,hwSiteName,hwSiteAdminAddr,hwNetIdentifier,hwSiteDescription,hwECMEquipId,hwECMEquipName,hwECMFatherEquipName            }
            STATUS current
            DESCRIPTION
                "HW Inverter ECM equipment alarm resume. 
                Its correlation binding parameters: 
                Site alarm serial number (SN),
                Alarm name,
                Alarm level,
                Site name,
                Site administrant address,
                NE ID,
                Site description,
                Additionally, in order to identify the device, equipment ID and equipment name are also include in VB(variable bondings)."
            ::= { hwHWInverterECMAlmTrapPrefix  2 }

        hwHWInverterAlmTrapTable OBJECT IDENTIFIER ::= { hwSiteAlarmTraps 26 }

        hwHWInverterAlmTrapPerfix  OBJECT IDENTIFIER ::= { hwHWInverterAlmTrapTable 0 }

        hwHWInverterAlarmTrap NOTIFICATION-TYPE
            OBJECTS { hwAlarmTrapOrdinalNumber,hwAlarmText,hwAlarmLevel,hwAlarmSigDesc,hwSiteName,hwSiteAdminAddr,hwNetIdentifier,hwSiteDescription,hwInverterModuleEquipId,hwInverterModuleEquipName,hwInverterModuleFatherEquipName            }
            STATUS current
            DESCRIPTION
                "HW general equipment alarm. 
                Its correlation binding parameters: 
                Site alarm serial number (SN),
                Alarm name,
                Alarm level,
                Site name,
                Site administrant address,
                NE ID,
                Site description,
                Additionally, in order to identify the device, equipment ID and equipment name are also include in VB(variable bondings)."
            ::= { hwHWInverterAlmTrapPerfix  1 }

        hwHWInverterAlarmResumeTrap NOTIFICATION-TYPE
            OBJECTS { hwAlarmTrapOrdinalNumber,hwAlarmText,hwAlarmLevel,hwAlarmSigDesc,hwSiteName,hwSiteAdminAddr,hwNetIdentifier,hwSiteDescription,hwInverterModuleEquipId,hwInverterModuleEquipName,hwInverterModuleFatherEquipName            }
            STATUS current
            DESCRIPTION
                "HW general alarm resume. 
                Its correlation binding parameters: 
                Site alarm serial number (SN),
                Alarm name,
                Alarm level,
                Site name,
                Site administrant address,
                NE ID,
                Site description,
                Additionally, in order to identify the device, equipment ID and equipment name are also include in VB(variable bondings)."
            ::= { hwHWInverterAlmTrapPerfix  2 }

        hwPowerControllerTrapTable OBJECT IDENTIFIER ::= { hwSiteAlarmTraps 30 }

        hwPowerControllerAlmTrapPrefix OBJECT IDENTIFIER ::= { hwPowerControllerTrapTable 0 }

        hwPowerControllerAlarmTrap NOTIFICATION-TYPE
            OBJECTS { hwAlarmTrapOrdinalNumber,hwAlarmText,hwAlarmLevel,hwAlarmSigDesc,hwSiteName,hwSiteAdminAddr,hwNetIdentifier,hwSiteDescription,hwPowerControllerEquipId,hwPowerControllerEquipName            }
            STATUS current
            DESCRIPTION
                "Power Controller alarm. 
                Its correlation binding parameters: 
                Site alarm serial number (SN),
                Alarm name,
                Alarm level,
                Site name,
                Site administrant address,
                NE ID,
                Site description,
                Additionally, in order to identify the device, Ac Ammeter equipment ID and equipment name are also include in VB(variable bondings)."
            ::= { hwPowerControllerAlmTrapPrefix 1 }

        hwPowerControllerAlarmResumeTrap NOTIFICATION-TYPE
            OBJECTS { hwAlarmTrapOrdinalNumber,hwAlarmText,hwAlarmLevel,hwAlarmSigDesc,hwSiteName,hwSiteAdminAddr,hwNetIdentifier,hwSiteDescription,hwPowerControllerEquipId,hwPowerControllerEquipName            }
            STATUS current
            DESCRIPTION
                "Power Controller alarm resume.  
                Its correlation binding parameters: 
                Site alarm serial number (SN),
                Alarm name,
                Alarm level,
                Site name,
                Site administrant address,
                NE ID,
                Site description,
                Additionally, in order to identify the device, Ac Ammeter  equipment ID and equipment name are also include in VB(variable bondings)."
            ::= { hwPowerControllerAlmTrapPrefix 2 }

        hwPVAdapterGroupAlmTrapTable OBJECT IDENTIFIER ::= { hwSiteAlarmTraps 38 }

        hwPVAdapterGroupAlmTrapPerfix  OBJECT IDENTIFIER ::= { hwPVAdapterGroupAlmTrapTable 0 }

        hwPVAdapterGroupAlarmTrap NOTIFICATION-TYPE
            OBJECTS { hwAlarmTrapOrdinalNumber,hwAlarmText,hwAlarmLevel,hwAlarmSigDesc,hwSiteName,hwSiteAdminAddr,hwNetIdentifier,hwSiteDescription,hwPVAdapterGroupEquipId,hwPVAdapterGroupEquipName            }
            STATUS current
            DESCRIPTION
                "PV Adapter alarm. 
                Its correlation binding parameters: 
                Site alarm serial number (SN),
                Alarm name,
                Alarm level,
                Site name,
                Site administrant address,
                NE ID,
                Site description,
                Additionally, in order to identify the device, Ac Ammeter equipment ID and equipment name are also include in VB(variable bondings)."
            ::= { hwPVAdapterGroupAlmTrapPerfix  1 }

        hwPVAdapterGroupAlarmResumeTrap NOTIFICATION-TYPE
            OBJECTS { hwAlarmTrapOrdinalNumber,hwAlarmText,hwAlarmLevel,hwAlarmSigDesc,hwSiteName,hwSiteAdminAddr,hwNetIdentifier,hwSiteDescription,hwPVAdapterGroupEquipId,hwPVAdapterGroupEquipName            }
            STATUS current
            DESCRIPTION
                "PV Adapter alarm resume.  
                Its correlation binding parameters: 
                Site alarm serial number (SN),
                Alarm name,
                Alarm level,
                Site name,
                Site administrant address,
                NE ID,
                Site description,
                Additionally, in order to identify the device, Ac Ammeter  equipment ID and equipment name are also include in VB(variable bondings)."
            ::= { hwPVAdapterGroupAlmTrapPerfix  2 }

        hwPVAdapterAlmTrapTable OBJECT IDENTIFIER ::= { hwSiteAlarmTraps 39 }

        hwPVAdapterAlmTrapPerfix  OBJECT IDENTIFIER ::= { hwPVAdapterAlmTrapTable 0 }

        hwPVAdapterAlarmTrap NOTIFICATION-TYPE
            OBJECTS { hwAlarmTrapOrdinalNumber,hwAlarmText,hwAlarmLevel,hwAlarmSigDesc,hwSiteName,hwSiteAdminAddr,hwNetIdentifier,hwSiteDescription,hwPVAdapterEquipId,hwPVAdapterEquipName            }
            STATUS current
            DESCRIPTION
                "PV Adapter alarm. 
                Its correlation binding parameters: 
                Site alarm serial number (SN),
                Alarm name,
                Alarm level,
                Site name,
                Site administrant address,
                NE ID,
                Site description,
                Additionally, in order to identify the device, Ac Ammeter equipment ID and equipment name are also include in VB(variable bondings)."
            ::= { hwPVAdapterAlmTrapPerfix  1 }

        hwPVAdapterAlarmResumeTrap NOTIFICATION-TYPE
            OBJECTS { hwAlarmTrapOrdinalNumber,hwAlarmText,hwAlarmLevel,hwAlarmSigDesc,hwSiteName,hwSiteAdminAddr,hwNetIdentifier,hwSiteDescription,hwPVAdapterEquipId,hwPVAdapterEquipName            }
            STATUS current
            DESCRIPTION
                "PV Adapter alarm resume.  
                Its correlation binding parameters: 
                Site alarm serial number (SN),
                Alarm name,
                Alarm level,
                Site name,
                Site administrant address,
                NE ID,
                Site description,
                Additionally, in order to identify the device, Ac Ammeter  equipment ID and equipment name are also include in VB(variable bondings)."
            ::= { hwPVAdapterAlmTrapPerfix  2 }

        hwSiteDevicesTraps OBJECT IDENTIFIER ::= { hwSiteMonitorMIBTraps 2 }

        hwDevicesTrapsPrefix OBJECT IDENTIFIER ::= { hwSiteDevicesTraps 0 }

        hwRectifiersInslotChange NOTIFICATION-TYPE
            OBJECTS { hwDeviceTrapOrdinalNumber,hwSiteName,hwSiteAdminAddr,hwNetIdentifier,hwSiteDescription,hwRectEquipId,hwRectEquipName,hwRectOperStatus            }
            STATUS current
            DESCRIPTION
                "When the presence status of a rectifier changes, the node reports an event. Then the NMS adds or deletes the corresponding entry to or from hwRectConfigTable or hwRectOperTable. The bound information includes the site address, site name, site description, and NE identifier. In addition, the ID, name, and status of the rectifier are bound to identify the specific rectifier and its operation type. When an entry is added, the device status is reported as normal (1); when an entry is deleted, the device status is reported as commFail (4).
                  This trap is the unique trigger condition that causes the NMS to add or delete entries to or from hwRectConfigTable or hwRectOperTable.
                "
            ::= { hwDevicesTrapsPrefix 1 }

        hwBatterysInslotChange NOTIFICATION-TYPE
            OBJECTS { hwDeviceTrapOrdinalNumber,hwSiteName,hwSiteAdminAddr,hwNetIdentifier,hwSiteDescription,hwBattStringEquipId,hwBattStringEquipName,hwBattStringOperStatus            }
            STATUS current
            DESCRIPTION
                "When the presence status of a battery string changes, the node reports an event. Then the NMS adds or deletes the corresponding entry to or from hwBatttConfigTable or hwBatttOperTable. The bound information includes the site address, site name, site description, and NE identifier. 
                In addition, the ID, name, and status of the battery string are bound to identify the specific battery string and its operation type. 
                When an entry is added, the device status is reported as normal (1); 
                when an entry is deleted, the device status is reported as loopBreak (4).
                  This trap is the unique trigger condition that causes the NMS to add or delete entries to or from hwBatttConfigTable or hwBatttOperTable."
            ::= { hwDevicesTrapsPrefix 2 }

        hwBattTestRecordsAdd NOTIFICATION-TYPE
            OBJECTS { hwDeviceTrapOrdinalNumber,hwSiteName,hwSiteAdminAddr,hwNetIdentifier,hwSiteDescription            }
            STATUS current
            DESCRIPTION
                "After a new discharge test is conducted on a battery group, the node reports an event. The bound information includes the site address, site name, site description, and NE identifier. The NMS needs to add the corresponding entry to the battery test table. The test records are sorted by time in descending order. The battery test table holds a maximum of 10 test records. If the number of test records exceeds 10, the earlier records starting from the last but one record are deleted at a time because the last record is saved permanently.
                  This trap is the unique trigger condition that causes the NMS to add entries from hwBattsTestResultTable.
                  The battery test table allows you only to add entries."
            ::= { hwDevicesTrapsPrefix 3 }

        hwEnvTempSensInslotChange NOTIFICATION-TYPE
            OBJECTS { hwDeviceTrapOrdinalNumber,hwSiteName,hwSiteAdminAddr,hwNetIdentifier,hwSiteDescription,hwEnvTempEquipId,hwEnvTempEquipName,hwEnvTempSensorOperStatus            }
            STATUS current
            DESCRIPTION
                "When the presence status of an environment temperature sensor changes, the node reports an event. Then the NMS adds or deletes the corresponding entry to or from hwEvnTempSensorTable. The bound information includes the site address, site name, site description, and NE identifier. In addition, the ID, name, and status of the environment temperature sensor are bound to identify the specific environment temperature sensor and its operation type. When an entry is added, the device status is reported as normal (1); when an entry is deleted, the device status is reported as notInslot (4).
                  This trap is the unique trigger condition that causes the NMS to add or delete entries to or from hwEnvTempSensorTable."
            ::= { hwDevicesTrapsPrefix 4 }

        hwEnvHumiSensInslotChange NOTIFICATION-TYPE
            OBJECTS { hwDeviceTrapOrdinalNumber,hwSiteName,hwSiteAdminAddr,hwNetIdentifier,hwSiteDescription,hwEnvHumiEquipId,hwEnvHumiEquipName,hwEnvHumiSensorOperStatus            }
            STATUS current
            DESCRIPTION
                "When the presence status of an environment humidity sensor changes, the trap reports an event. Then the NMS adds or deletes the corresponding entry to or from hwEvnHumiSensorTable. The bound information includes the site address, site name, site description, and NE identifier. In addition, the ID, name, and status of the environment humidity sensor are bound to identify the specific environment humidity sensor and its operation type. When an entry is added, the device status is reported as normal (1); when an entry is deleted, the device status is reported as notInslot (4).
                  This trap is the unique trigger condition that causes the NMS to add or delete entries to or from hwEnvHumiSensorTable."
            ::= { hwDevicesTrapsPrefix 5 }

        hwPDEsInslotChange NOTIFICATION-TYPE
            OBJECTS { hwDeviceTrapOrdinalNumber,hwSiteName,hwSiteAdminAddr,hwNetIdentifier,hwSiteDescription            }
            STATUS current
            DESCRIPTION
                "Description."
            ::= { hwDevicesTrapsPrefix 6 }

        hwInvertersInslotChange NOTIFICATION-TYPE
            OBJECTS { hwDeviceTrapOrdinalNumber,hwSiteName,hwSiteAdminAddr,hwNetIdentifier,hwSiteDescription,hwInverterEquipId,hwInverterEquipName,hwInverterOperStatus            }
            STATUS current
            DESCRIPTION
                "Description."
            ::= { hwDevicesTrapsPrefix 7 }

        hwSiteStatusTrap OBJECT IDENTIFIER ::= { hwSiteMonitorMIBTraps 3 }

        hwSiteStatusTrapPrefix OBJECT IDENTIFIER ::= { hwSiteStatusTrap 0 }

        hwAcInputFaultTrap NOTIFICATION-TYPE
            OBJECTS { hwAlarmTrapOrdinalNumber,hwAlarmText,hwAlarmLevel,hwAlarmSigDesc,hwSiteName,hwSiteAdminAddr,hwNetIdentifier,hwSiteDescription,hwAcEquipId,hwAcEquipName,hwAcFatherEquipname,hwAcInputOperStatus,hwAcInputStatus            }
            STATUS current
            DESCRIPTION
                ""
            ::= { hwSiteStatusTrapPrefix 1 }

        hwRectifierFaultTrap NOTIFICATION-TYPE
            OBJECTS { hwAlarmTrapOrdinalNumber,hwAlarmText,hwAlarmLevel,hwAlarmSigDesc,hwSiteName,hwSiteAdminAddr,hwNetIdentifier,hwSiteDescription,hwRectifierStatus            }
            STATUS current
            DESCRIPTION
                ""
            ::= { hwSiteStatusTrapPrefix 2 }

        hwBatteryDischargeTrap NOTIFICATION-TYPE
            OBJECTS { hwAlarmTrapOrdinalNumber,hwAlarmText,hwAlarmLevel,hwAlarmSigDesc,hwSiteName,hwSiteAdminAddr,hwNetIdentifier,hwSiteDescription,hwBattsGroupId,hwBattsGroupName,hwBatteryDischarge            }
            STATUS current
            DESCRIPTION
                ""
            ::= { hwSiteStatusTrapPrefix 3 }

        hwBatteryLowVoltageTrap NOTIFICATION-TYPE
            OBJECTS { hwAlarmTrapOrdinalNumber,hwAlarmText,hwAlarmLevel,hwAlarmSigDesc,hwSiteName,hwSiteAdminAddr,hwNetIdentifier,hwSiteDescription,hwBatteryLowVoltage            }
            STATUS current
            DESCRIPTION
                ""
            ::= { hwSiteStatusTrapPrefix 4 }

        hwBatteryUltraLowVoltageTrap NOTIFICATION-TYPE
            OBJECTS { hwAlarmTrapOrdinalNumber,hwAlarmText,hwAlarmLevel,hwAlarmSigDesc,hwSiteName,hwSiteAdminAddr,hwNetIdentifier,hwSiteDescription,hwBatteryUltraLowVoltage            }
            STATUS current
            DESCRIPTION
                ""
            ::= { hwSiteStatusTrapPrefix 5 }

        hwBatteryDisconnectTrap NOTIFICATION-TYPE
            OBJECTS { hwAlarmTrapOrdinalNumber,hwAlarmText,hwAlarmLevel,hwAlarmSigDesc,hwSiteName,hwSiteAdminAddr,hwNetIdentifier,hwSiteDescription,hwBatteryDisconnect            }
            STATUS current
            DESCRIPTION
                ""
            ::= { hwSiteStatusTrapPrefix 6 }

        hwFuseBrokenTrap NOTIFICATION-TYPE
            OBJECTS { hwAlarmTrapOrdinalNumber,hwAlarmText,hwAlarmLevel,hwAlarmSigDesc,hwSiteName,hwSiteAdminAddr,hwNetIdentifier,hwSiteDescription,hwFuseBroken            }
            STATUS current
            DESCRIPTION
                ""
            ::= { hwSiteStatusTrapPrefix 7 }

        hwLowRecitiferCapacityTrap NOTIFICATION-TYPE
            OBJECTS { hwAlarmTrapOrdinalNumber,hwAlarmText,hwAlarmLevel,hwAlarmSigDesc,hwSiteName,hwSiteAdminAddr,hwNetIdentifier,hwSiteDescription,hwRectsGroupId,hwRectsGroupName,hwLowRecitiferCapacity            }
            STATUS current
            DESCRIPTION
                ""
            ::= { hwSiteStatusTrapPrefix 8 }

        hwBatteryTestNegativeTrap NOTIFICATION-TYPE
            OBJECTS { hwAlarmTrapOrdinalNumber,hwAlarmText,hwAlarmLevel,hwAlarmSigDesc,hwSiteName,hwSiteAdminAddr,hwNetIdentifier,hwSiteDescription,hwBattsGroupId,hwBattsGroupName,hwBatteryTestNegative            }
            STATUS current
            DESCRIPTION
                ""
            ::= { hwSiteStatusTrapPrefix 9 }

        hwUrgentAlarmTrap NOTIFICATION-TYPE
            OBJECTS { hwAlarmTrapOrdinalNumber,hwAlarmText,hwAlarmLevel,hwAlarmSigDesc,hwSiteName,hwSiteAdminAddr,hwNetIdentifier,hwSiteDescription,hwUrgentAlarmStatus            }
            STATUS current
            DESCRIPTION
                ""
            ::= { hwSiteStatusTrapPrefix 10 }

        hwNonurgentAlarmTrap NOTIFICATION-TYPE
            OBJECTS { hwAlarmTrapOrdinalNumber,hwAlarmText,hwAlarmLevel,hwAlarmSigDesc,hwSiteName,hwSiteAdminAddr,hwNetIdentifier,hwSiteDescription,hwNonurgentAlarmStatus            }
            STATUS current
            DESCRIPTION
                ""
            ::= { hwSiteStatusTrapPrefix 11 }

        hwSiteEquip OBJECT IDENTIFIER ::= { hwSiteMonitorMIB 3 }

        hwSiteCameraTable OBJECT-TYPE
            SYNTAX SEQUENCE OF HwSiteCameraEntry
            MAX-ACCESS not-accessible
             STATUS current
             DESCRIPTION
                "/"
            ::= { hwSiteEquip 1 }

        hwSiteCameraEntry OBJECT-TYPE
                        SYNTAX HwSiteCameraEntry
            MAX-ACCESS not-accessible
             STATUS current
             DESCRIPTION
                "/"
            INDEX { hwSiteCameraIp }
            ::= { hwSiteCameraTable 1 }

        HwSiteCameraEntry            ::= SEQUENCE {
                hwSiteCameraIp
                    OCTET STRING,
                hwSiteCameraPort
                    INTEGER,
                hwSiteCameraPhotSetAlarmType
                    INTEGER,
                hwSiteCameraAssociatedAlarmPicture1
                    OCTET STRING,
                hwSiteCameraAssociatedAlarmPicture2
                    OCTET STRING,
                hwSiteCameraAssociatedAlarmPicture3
                    OCTET STRING,
                hwSiteCameraAssociatedAlarmPicture4
                    OCTET STRING,
                hwSiteCameraAssociatedAlarmPicture5
                    OCTET STRING,
                hwSiteCameraAssociatedAlarmPicture6
                    OCTET STRING,
                hwSiteCameraAssociatedAlarmPicture7
                    OCTET STRING,
                hwSiteCameraAssociatedAlarmPicture8
                    OCTET STRING,
                hwSiteCameraAssociatedAlarmPicture9
                    OCTET STRING,
                hwSiteCameraAssociatedAlarmPicture10
                    OCTET STRING,
                hwSiteCameraAdditionalAssociatedAlarmPictures
                    OCTET STRING
            }

        hwSiteCameraIp OBJECT-TYPE
            SYNTAX OCTET STRING
            MAX-ACCESS read-only
            STATUS current
            DESCRIPTION
                "the camera ip adress."
            ::= { hwSiteCameraEntry 1 }

        hwSiteCameraPort OBJECT-TYPE
            SYNTAX INTEGER
                {
                nim1com1(1),
                nim1com2(2),
                nim2com1(3),
                nim2com2(4)
                }
            MAX-ACCESS read-only
            STATUS current
            DESCRIPTION
                "camera connect port number."
            ::= { hwSiteCameraEntry 2 }

        hwSiteCameraPhotSetAlarmType OBJECT-TYPE
            SYNTAX INTEGER
                {
                dooralarm(1),
                smokealarm(2),
                wateralarm(3),
                motiondetectalarm(4)
                }
            MAX-ACCESS read-write
            STATUS current
            DESCRIPTION
                "You can set the alarm type to obtain the historical picture of the camera-related alarm shooting."
            ::= { hwSiteCameraEntry 5 }

        hwSiteCameraAssociatedAlarmPicture1 OBJECT-TYPE
            SYNTAX OCTET STRING
            MAX-ACCESS read-only
            STATUS current
            DESCRIPTION
                "Associated alarm picture 1."
            ::= { hwSiteCameraEntry 6 }

        hwSiteCameraAssociatedAlarmPicture2 OBJECT-TYPE
            SYNTAX OCTET STRING
            MAX-ACCESS read-only
            STATUS current
            DESCRIPTION
                "Associated alarm picture 2."
            ::= { hwSiteCameraEntry 7 }

        hwSiteCameraAssociatedAlarmPicture3 OBJECT-TYPE
            SYNTAX OCTET STRING
            MAX-ACCESS read-only
            STATUS current
            DESCRIPTION
                "Associated alarm picture 3."
            ::= { hwSiteCameraEntry 8 }

        hwSiteCameraAssociatedAlarmPicture4 OBJECT-TYPE
            SYNTAX OCTET STRING
            MAX-ACCESS read-only
            STATUS current
            DESCRIPTION
                "Associated alarm picture 4."
            ::= { hwSiteCameraEntry 9 }

        hwSiteCameraAssociatedAlarmPicture5 OBJECT-TYPE
            SYNTAX OCTET STRING
            MAX-ACCESS read-only
            STATUS current
            DESCRIPTION
                "Associated alarm picture 5."
            ::= { hwSiteCameraEntry 10 }

        hwSiteCameraAssociatedAlarmPicture6 OBJECT-TYPE
            SYNTAX OCTET STRING
            MAX-ACCESS read-only
            STATUS current
            DESCRIPTION
                "Associated alarm picture 6."
            ::= { hwSiteCameraEntry 11 }

        hwSiteCameraAssociatedAlarmPicture7 OBJECT-TYPE
            SYNTAX OCTET STRING
            MAX-ACCESS read-only
            STATUS current
            DESCRIPTION
                "Associated alarm picture 7."
            ::= { hwSiteCameraEntry 12 }

        hwSiteCameraAssociatedAlarmPicture8 OBJECT-TYPE
            SYNTAX OCTET STRING
            MAX-ACCESS read-only
            STATUS current
            DESCRIPTION
                "Associated alarm picture 8."
            ::= { hwSiteCameraEntry 13 }

        hwSiteCameraAssociatedAlarmPicture9 OBJECT-TYPE
            SYNTAX OCTET STRING
            MAX-ACCESS read-only
            STATUS current
            DESCRIPTION
                "Associated alarm picture 9."
            ::= { hwSiteCameraEntry 14 }

        hwSiteCameraAssociatedAlarmPicture10 OBJECT-TYPE
            SYNTAX OCTET STRING
            MAX-ACCESS read-only
            STATUS current
            DESCRIPTION
                "Associated alarm picture 10."
            ::= { hwSiteCameraEntry 15 }

        hwSiteCameraAdditionalAssociatedAlarmPictures OBJECT-TYPE
            SYNTAX OCTET STRING
            MAX-ACCESS read-only
            STATUS current
            DESCRIPTION
                "Additional associated alarm pictures."
            ::= { hwSiteCameraEntry 16 }

END
